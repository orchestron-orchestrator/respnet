module junos-conf-protocols {
  yang-version "1";
  namespace "http://yang.juniper.net/junos/conf/protocols";
  prefix "jc-protocols";
  import junos-common-types {
    prefix "jt";
    revision-date 2023-01-01;
  }
  import junos-conf-root {
    prefix "jc";
    revision-date 2023-01-01;
  }
  organization "Juniper Networks, Inc.";
  contact "yang-support@juniper.net";
  description "Junos protocols configuration module";
  revision 2023-01-01 {
    description "Junos: 23.4R1.10";
  }
  augment "/jc:configuration" {
    uses protocols-group;
  }
  grouping protocols-group {
    container protocols {
      description "Routing protocol configuration";
      uses juniper-protocols;
    }
  }
  grouping juniper-protocols {
    container bgp {
      description "BGP options";
      uses juniper-protocols-bgp;
    }
    container isis {
      description "IS-IS options";
      uses juniper-protocols-isis;
    }
    container ldp {
      description "LDP options";
      uses juniper-protocols-ldp;
    }
    container mpls {
      description "Multiprotocol Label Switching options";
      uses juniper-protocols-mpls;
    }
  }
  grouping admin_group_include_exclude {
    choice include-any-choice {
      case case_1 {
        leaf-list include-any {
          type string;
          description "Groups, one or more of which must be present";
          ordered-by user;
        }
      }
    }
    choice include-all-choice {
      case case_1 {
        leaf-list include-all {
          type string;
          description "Groups, all of which must be present";
          ordered-by user;
        }
      }
    }
    choice exclude-choice {
      case case_1 {
        leaf-list exclude {
          type string;
          description "Groups, all of which must be absent";
          ordered-by user;
        }
      }
    }
  }
  grouping apply-advanced {
    description "Apply advanced configuration logic";
    leaf-list apply-groups {
      type string;
      description "Groups from which to inherit configuration data";
      ordered-by user;
    }
    leaf-list apply-groups-except {
      type string;
      description "Don't inherit configuration data from these groups";
      ordered-by user;
    }
    list apply-macro {
      description "Macro and parameters for commit script expansion";
      key name;
      ordered-by user;
      uses apply-macro-type;
    }
  }
  grouping apply-macro-type {
    description "Macro data for commit-script expansion";
    leaf name {
      type string;
      description "Name of the macro to be expanded";
    }
    list data {
      key name;
      uses macro-data-type;
    }
  }
  grouping bandwidth-type {
    leaf per-traffic-class-bandwidth {
      type string;
      description "Bandwidth to reserve";
      units bps;
    }
    leaf ct0 {
      type string;
      description "Bandwidth from traffic class 0";
      units bps;
    }
    leaf ct1 {
      type string;
      description "Bandwidth from traffic class 1";
      units bps;
    }
    leaf ct2 {
      type string;
      description "Bandwidth from traffic class 2";
      units bps;
    }
    leaf ct3 {
      type string;
      description "Bandwidth from traffic class 3";
      units bps;
    }
  }
  grouping cfm-traceoptions {
    description "Trace options for connectivity fault management";
    leaf no-remote-trace {
      type empty;
      description "Disable remote tracing";
    }
    container file {
      description "Trace file information";
      leaf filename {
        type string {
          length "1 .. 1024";
        }
        description "Name of file in which to write trace information";
      }
      leaf size {
        type string;
        description "Maximum trace file size";
      }
      leaf files {
        type uint32 {
          range "2 .. 1000";
        }
        default "3";
        description "Maximum number of trace files";
      }
      choice world-readable-choice {
        leaf world-readable {
          type empty;
          description "Allow any user to read the log file";
        }
        leaf no-world-readable {
          type empty;
          description "Don't allow any user to read the log file";
        }
      }
      leaf match {
        type "jt:regular-expression";
        description "Regular expression for lines to be logged";
      }
    }
    list flag {
      description "Tracing parameters";
      key name;
      ordered-by user;
      leaf name {
        type enumeration {
          enum configuration {
            description "Trace configuration events";
          }
          enum routing-socket {
            description "Trace routing socket events";
          }
          enum protocol {
            description "Trace protocol processing events";
          }
          enum init {
            description "Trace events related to protocol daemon start-up";
          }
          enum error {
            description "Trace events related to catestrophic errors in daemon";
          }
          enum issu {
            description "Trace ISSU related events";
          }
          enum all {
            description "Trace everything";
          }
        }
      }
    }
  }
  grouping civic-address-elements {
    leaf what {
      type uint16 {
        range "0 .. 2";
      }
      default "1";
      description "Type of address";
    }
    leaf country-code {
      type string {
        length "2";
      }
      description "Two-letter country code";
    }
    list ca-type {
      key name;
      ordered-by user;
      leaf name {
        type uint16 {
          range "0 .. 255";
        }
        description "Address element type";
      }
      leaf ca-value {
        type string {
          length "1 .. 248";
        }
        description "Address element value";
      }
    }
  }
  grouping clksync-traceoptions {
    description "Trace options for syncE and PTP";
    leaf no-remote-trace {
      type empty;
      description "Disable remote tracing";
    }
    container file {
      description "Trace file information";
      leaf filename {
        type string {
          length "1 .. 1024";
        }
        description "Name of file in which to write trace information";
      }
      leaf size {
        type string;
        description "Maximum trace file size";
      }
      leaf files {
        type uint32 {
          range "2 .. 1000";
        }
        default "3";
        description "Maximum number of trace files";
      }
      choice world-readable-choice {
        leaf world-readable {
          type empty;
          description "Allow any user to read the log file";
        }
        leaf no-world-readable {
          type empty;
          description "Don't allow any user to read the log file";
        }
      }
      leaf match {
        type "jt:regular-expression";
        description "Regular expression for lines to be logged";
      }
    }
    list flag {
      description "Tracing parameters";
      key name;
      ordered-by user;
      leaf name {
        type enumeration {
          enum init {
            description "Trace daemon start-up related events";
          }
          enum routing-socket {
            description "Trace routing-socket events";
          }
          enum synchronization {
            description "Trace esmc protocol events only";
          }
          enum ptp {
            description "Trace ptp protocol events only";
          }
          enum protocol {
            description "Trace protocol events";
          }
          enum configuration {
            description "Trace configuration events";
          }
          enum debug {
            description "Trace generic debug events";
          }
          enum ppm {
            description "Trace periodic packet management events";
          }
          enum error {
            description "Trace error events";
          }
          enum hybrid {
            description "Trace hybrid events";
          }
          enum framer {
            description "Trace BITS framer events";
          }
          enum ipc {
            description "Trace IPC messages";
          }
          enum all {
            description "Trace everything";
          }
        }
      }
    }
  }
  grouping co-ordinate-elements {
    description "Geographical co-ordinates";
    leaf longitude {
      type uint16 {
        range "0 .. 360";
      }
      description "Longitude value";
    }
    leaf lattitude {
      type uint16 {
        range "0 .. 360";
      }
      description "Lattitude value";
    }
  }
  grouping juniper-default-ri-protocols-igmp-snooping {
    description "IGMP snooping options";
    list vlan {
      description "VLAN options";
      key name;
      ordered-by user;
      leaf name {
        type string;
        description "VLAN name";
      }
      container traceoptions {
        description "Trace options for IGMP Snooping";
        container file {
          description "Trace file options";
          leaf filename {
            type string {
              length "1 .. 1024";
            }
            description "Name of file in which to write trace information";
          }
          leaf replace {
            type empty;
            description "Replace trace file rather than appending to it";
            status deprecated;
          }
          leaf size {
            type string;
            description "Maximum trace file size";
          }
          leaf files {
            type uint32 {
              range "2 .. 1000";
            }
            default "10";
            description "Maximum number of trace files";
          }
          leaf no-stamp {
            type empty;
            description "Do not timestamp trace file";
            status deprecated;
          }
          choice world-readable-choice {
            leaf world-readable {
              type empty;
              description "Allow any user to read the log file";
            }
            leaf no-world-readable {
              type empty;
              description "Don't allow any user to read the log file";
            }
          }
        }
        list flag {
          description "Tracing parameters";
          key name;
          ordered-by user;
          leaf name {
            type enumeration {
              enum packets {
                description "Trace all IGMP packets";
              }
              enum query {
                description "Trace IGMP membership query messages";
              }
              enum report {
                description "Trace membership report messages";
              }
              enum leave {
                description "Trace leave group messages (IGMPv2 only)";
              }
              enum group {
                description "Trace group operations";
              }
              enum client-notification {
                description "Trace notifications";
              }
              enum route {
                description "Trace routing information";
              }
              enum normal {
                description "Trace normal events";
              }
              enum general {
                description "Trace general events";
              }
              enum state {
                description "Trace state transitions";
              }
              enum task {
                description "Trace routing protocol task processing";
              }
              enum timer {
                description "Trace routing protocol timer processing";
              }
              enum all {
                description "Trace everything";
              }
            }
          }
          leaf send {
            type empty;
            description "Trace transmitted packets";
          }
          leaf receive {
            type empty;
            description "Trace received packets";
          }
          leaf detail {
            type empty;
            description "Trace detailed information";
          }
          leaf disable {
            type empty;
            description "Disable this trace flag";
          }
        }
      }
      leaf query-interval {
        type uint32 {
          range "1 .. 1024";
        }
        default "125";
        description "When to send host query messages";
        units seconds;
      }
      container l2-querier {
        description "Enable L2 querier mode";
        leaf source-address {
          type "jt:ipv4addr";
          description "Source IP address to use for L2 querier";
        }
      }
      leaf query-response-interval {
        type string;
        default "10";
        description "How long to wait for a host query response";
        units seconds;
      }
      leaf query-last-member-interval {
        type string;
        default "1";
        description "When to send group query messages";
        units seconds;
      }
      leaf robust-count {
        type uint32 {
          range "2 .. 10";
        }
        default "2";
        description "Expected packet loss on a subnet";
      }
      leaf immediate-leave {
        type empty;
        description "Enable immediate group leave on interfaces";
      }
      container proxy {
        description "Enable proxy mode";
        presence "enable proxy";
        leaf source-address {
          type "jt:ipv4addr";
          description "Source IP address to use for proxy";
        }
      }
      leaf evpn-ssm-reports-only {
        type empty;
        description "Accept and process only <s,g> reports of SSM groups";
      }
      container data-forwarding {
        description "MVR Data forwarding options";
        choice source_receiver {
          case case_1 {
            container source {
              description "MVR source vlan";
              leaf groups {
                type "jt:ipv4prefix";
                description "Group range";
              }
            }
          }
          case case_2 {
            container receiver {
              description "MVR receiver vlan";
              choice enab_disab_translate {
                case case_1 {
                  leaf translate {
                    type empty;
                    description "Translate vid of outgoing pkt to receiver vlan's tag";
                  }
                }
              }
              list source-list {
                description "Source VLANs for this receiver vlan";
                key name;
                ordered-by user;
                leaf name {
                  type string;
                  description "VLAN name";
                }
              }
              leaf install {
                type empty;
                description "Install forwarded bridging entires";
              }
              leaf mode {
                type enumeration {
                  enum transparent {
                    description "MVR Transparent Mode";
                  }
                  enum proxy {
                    description "MVR Proxy Mode";
                  }
                }
                default "transparent";
                description "MVR Mode";
              }
            }
          }
        }
      }
      list interface {
        description "Interface options for IGMP";
        key name;
        ordered-by user;
        leaf name {
          type "jt:interface-name";
          description "Interface name";
        }
        leaf multicast-router-interface {
          type empty;
          description "Enabling multicast-router-interface on the interface";
        }
        leaf immediate-leave {
          type empty;
          description "Enable immediate group leave on interface";
        }
        leaf host-only-interface {
          type empty;
          description "Enable interface to be treated as host-side interface";
        }
        leaf group-limit {
          type uint16;
          description "Maximum number of groups an interface can join";
        }
        container static {
          description "Static group or source membership";
          list group {
            description "IP multicast group address";
            key name;
            ordered-by user;
            leaf name {
              type "jt:ipv4addr";
              description "IP multicast group address";
            }
            list source {
              description "IP multicast source address";
              key name;
              ordered-by user;
              leaf name {
                type "jt:ipv4addr";
                description "Source address of IP multicast data";
              }
            }
          }
        }
      }
      list qualified-vlan {
        description "VLAN options for qualified-learning";
        key name;
        ordered-by user;
        leaf name {
          type uint32 {
            range "0 .. 1023";
          }
          description "VLAN ID of the learning-domain";
        }
        leaf query-interval {
          type uint32 {
            range "1 .. 1024";
          }
          description "When to send host query messages";
          units seconds;
        }
        container l2-querier {
          description "Enable L2 querier mode";
          leaf source-address {
            type "jt:ipv4addr";
            description "Source IP address to use for L2 querier";
          }
        }
        leaf query-response-interval {
          type string;
          description "How long to wait for a host query response";
          units seconds;
        }
        leaf query-last-member-interval {
          type string;
          description "When to send group query messages";
          units seconds;
        }
        leaf robust-count {
          type uint32 {
            range "2 .. 10";
          }
          description "Expected packet loss on a subnet";
        }
        leaf immediate-leave {
          type empty;
          description "Enable immediate group leave on interfaces";
        }
        container proxy {
          description "Enable proxy mode";
          presence "enable proxy";
          leaf source-address {
            type "jt:ipv4addr";
            description "Source IP address to use for proxy";
          }
        }
        leaf evpn-ssm-reports-only {
          type empty;
          description "Accept and process only <s,g> reports of SSM groups";
        }
        list interface {
          description "Interface options for IGMP";
          key name;
          ordered-by user;
          leaf name {
            type "jt:interface-name";
            description "Interface name";
          }
          leaf multicast-router-interface {
            type empty;
            description "Enabling multicast-router-interface on the interface";
          }
          leaf immediate-leave {
            type empty;
            description "Enable immediate group leave on interface";
          }
          leaf host-only-interface {
            type empty;
            description "Enable interface to be treated as host-side interface";
          }
          leaf group-limit {
            type uint16;
            description "Maximum number of groups an interface can join";
          }
          container static {
            description "Static group or source membership";
            list group {
              description "IP multicast group address";
              key name;
              ordered-by user;
              leaf name {
                type "jt:ipv4addr";
                description "IP multicast group address";
              }
              list source {
                description "IP multicast source address";
                key name;
                ordered-by user;
                leaf name {
                  type "jt:ipv4addr";
                  description "Source address of IP multicast data";
                }
              }
            }
          }
        }
      }
      leaf version {
        type uint8 {
          range "2 .. 3";
        }
        description "Set IGMP version number on interface_help_string";
      }
    }
    container traceoptions {
      description "Trace options for IGMP Snooping";
      container file {
        description "Trace file options";
        leaf filename {
          type string {
            length "1 .. 1024";
          }
          description "Name of file in which to write trace information";
        }
        leaf replace {
          type empty;
          description "Replace trace file rather than appending to it";
          status deprecated;
        }
        leaf size {
          type string;
          description "Maximum trace file size";
        }
        leaf files {
          type uint32 {
            range "2 .. 1000";
          }
          default "10";
          description "Maximum number of trace files";
        }
        leaf no-stamp {
          type empty;
          description "Do not timestamp trace file";
          status deprecated;
        }
        choice world-readable-choice {
          leaf world-readable {
            type empty;
            description "Allow any user to read the log file";
          }
          leaf no-world-readable {
            type empty;
            description "Don't allow any user to read the log file";
          }
        }
      }
      list flag {
        description "Tracing parameters";
        key name;
        ordered-by user;
        leaf name {
          type enumeration {
            enum packets {
              description "Trace all IGMP packets";
            }
            enum query {
              description "Trace IGMP membership query messages";
            }
            enum report {
              description "Trace membership report messages";
            }
            enum leave {
              description "Trace leave group messages (IGMPv2 only)";
            }
            enum group {
              description "Trace group operations";
            }
            enum client-notification {
              description "Trace notifications";
            }
            enum host-notification {
              description "Trace host notifications";
            }
            enum route {
              description "Trace routing information";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
        leaf send {
          type empty;
          description "Trace transmitted packets";
        }
        leaf receive {
          type empty;
          description "Trace received packets";
        }
        leaf detail {
          type empty;
          description "Trace detailed information";
        }
        leaf disable {
          type empty;
          description "Disable this trace flag";
        }
      }
    }
    leaf query-interval {
      type uint32 {
        range "1 .. 1024";
      }
      default "125";
      description "When to send host query messages";
      units seconds;
    }
    leaf query-response-interval {
      type string;
      default "10";
      description "How long to wait for a host query response";
      units seconds;
    }
    leaf query-last-member-interval {
      type string;
      default "1";
      description "When to send group query messages";
      units seconds;
    }
    leaf robust-count {
      type uint32 {
        range "2 .. 10";
      }
      default "2";
      description "Expected packet loss on a subnet";
    }
    leaf immediate-leave {
      type empty;
      description "Enable immediate group leave on interfaces";
    }
    leaf evpn-ssm-reports-only {
      type empty;
      description "Accept and process only <s,g> reports of SSM groups";
    }
    leaf version {
      type uint8 {
        range "2 .. 3";
      }
      description "Set IGMP snooping version number";
    }
    container proxy {
      description "Enable proxy mode";
      presence "enable proxy";
      leaf source-address {
        type "jt:ipv4addr";
        description "Source IP address to use for proxy";
      }
      leaf irb {
        type empty;
        description "Proxy IGMP reports to IRB";
      }
    }
    list interface {
      description "Interface options for IGMP";
      key name;
      ordered-by user;
      leaf name {
        type "jt:interface-name";
        description "Interface name";
      }
      leaf multicast-router-interface {
        type empty;
        description "Enabling multicast-router-interface on the interface";
      }
      leaf immediate-leave {
        type empty;
        description "Enable immediate group leave on interfaces";
      }
      leaf host-only-interface {
        type empty;
        description "Enable interfaces to be treated as host-side interfaces";
      }
      leaf group-limit {
        type uint16 {
          range "1 .. 65535";
        }
        description "Maximum number of (source,group) per interface";
      }
      container static {
        description "Static group or source membership";
        list group {
          description "IP multicast group address";
          key name;
          ordered-by user;
          leaf name {
            type "jt:ipv4addr";
            description "IP multicast group address";
          }
          list source {
            description "IP multicast source address";
            key name;
            ordered-by user;
            leaf name {
              type "jt:ipv4addr";
              description "Source address of IP multicast data";
            }
          }
        }
      }
    }
  }
  grouping juniper-default-ri-protocols-mld-snooping {
    description "MLD snooping options";
    list vlan {
      description "VLAN options";
      key name;
      ordered-by user;
      leaf name {
        type string;
        description "VLAN name";
      }
      container traceoptions {
        description "Trace options for MLD Snooping";
        container file {
          description "Trace file options";
          leaf filename {
            type string {
              length "1 .. 1024";
            }
            description "Name of file in which to write trace information";
          }
          leaf replace {
            type empty;
            description "Replace trace file rather than appending to it";
            status deprecated;
          }
          leaf size {
            type string;
            description "Maximum trace file size";
          }
          leaf files {
            type uint32 {
              range "2 .. 1000";
            }
            default "10";
            description "Maximum number of trace files";
          }
          leaf no-stamp {
            type empty;
            description "Do not timestamp trace file";
            status deprecated;
          }
          choice world-readable-choice {
            leaf world-readable {
              type empty;
              description "Allow any user to read the log file";
            }
            leaf no-world-readable {
              type empty;
              description "Don't allow any user to read the log file";
            }
          }
        }
        list flag {
          description "Tracing parameters";
          key name;
          ordered-by user;
          leaf name {
            type enumeration {
              enum packets {
                description "Trace all MLD packets";
              }
              enum query {
                description "Trace MLD membership query messages";
              }
              enum report {
                description "Trace membership report messages";
              }
              enum leave {
                description "Trace leave group messages (MLDv1 only)";
              }
              enum group {
                description "Trace group operations";
              }
              enum client-notification {
                description "Trace notifications";
              }
              enum host-notification {
                description "Trace host notifications";
              }
              enum route {
                description "Trace routing information";
              }
              enum normal {
                description "Trace normal events";
              }
              enum general {
                description "Trace general events";
              }
              enum state {
                description "Trace state transitions";
              }
              enum policy {
                description "Trace policy processing";
              }
              enum task {
                description "Trace routing protocol task processing";
              }
              enum timer {
                description "Trace routing protocol timer processing";
              }
              enum all {
                description "Trace everything";
              }
            }
          }
          leaf send {
            type empty;
            description "Trace transmitted packets";
          }
          leaf receive {
            type empty;
            description "Trace received packets";
          }
          leaf detail {
            type empty;
            description "Trace detailed information";
          }
          leaf disable {
            type empty;
            description "Disable this trace flag";
          }
        }
      }
      leaf query-interval {
        type uint32 {
          range "1 .. 1024";
        }
        default "125";
        description "When to send host query messages";
        units seconds;
      }
      container l2-querier {
        description "Enable L2 querier mode";
        leaf source-address {
          type "jt:ipv6addr";
          description "Source IP address to use for L2 querier";
        }
      }
      leaf query-response-interval {
        type string;
        default "10";
        description "How long to wait for a host query response";
        units seconds;
      }
      leaf query-last-member-interval {
        type string;
        default "1";
        description "When to send group query messages";
        units seconds;
      }
      leaf robust-count {
        type uint32 {
          range "2 .. 10";
        }
        default "2";
        description "Expected packet loss on a subnet";
      }
      leaf immediate-leave {
        type empty;
        description "Enable immediate group leave on interfaces";
      }
      container proxy {
        description "Enable proxy mode";
        leaf source-address {
          type "jt:ipv6addr";
          description "Source IP address to use for proxy";
        }
      }
      leaf evpn-ssm-reports-only {
        type empty;
        description "Accept and process only <s,g> reports of SSM groups";
      }
      leaf version {
        type uint8 {
          range "1 .. 2";
        }
        description "Set MLD snooping version number";
      }
      list interface {
        description "Interface options for MLD";
        key name;
        ordered-by user;
        leaf name {
          type "jt:interface-name";
          description "Interface name";
        }
        leaf multicast-router-interface {
          type empty;
          description "Enabling multicast-router-interface on the interface";
        }
        leaf immediate-leave {
          type empty;
          description "Enable immediate group leave on interfaces";
        }
        leaf host-only-interface {
          type empty;
          description "Enable interfaces to be treated as host-side interfaces";
        }
        leaf group-limit {
          type uint16;
          description "Maximum number of groups an interface can join";
        }
        container static {
          description "Static group or source membership";
          list group {
            description "IP multicast group address";
            key name;
            ordered-by user;
            leaf name {
              type "jt:ipv6addr";
              description "IP multicast group address";
            }
            list source {
              description "IP multicast source address";
              key name;
              ordered-by user;
              leaf name {
                type "jt:ipv6addr";
                description "Source address of IP multicast data";
              }
            }
          }
        }
      }
      list qualified-vlan {
        description "VLAN options for qualified-learning";
        key name;
        ordered-by user;
        leaf name {
          type uint32 {
            range "0 .. 1023";
          }
          description "VLAN ID of the learning-domain";
        }
        leaf query-interval {
          type uint32 {
            range "1 .. 1024";
          }
          description "When to send host query messages";
          units seconds;
        }
        container l2-querier {
          leaf source-address {
            type "jt:ipv6addr";
            description "Source IP address to use for L2 querier";
          }
        }
        leaf query-response-interval {
          type string;
          description "How long to wait for a host query response";
          units seconds;
        }
        leaf query-last-member-interval {
          type string;
          description "When to send group query messages";
          units seconds;
        }
        leaf robust-count {
          type uint32 {
            range "2 .. 10";
          }
          description "Expected packet loss on a subnet";
        }
        leaf immediate-leave {
          type empty;
          description "Enable immediate group leave on interfaces";
        }
        container proxy {
          description "Enable proxy mode";
          leaf source-address {
            type "jt:ipv6addr";
            description "Source IP address to use for proxy";
          }
        }
        leaf evpn-ssm-reports-only {
          type empty;
          description "Accept and process only <s,g> reports of SSM groups";
        }
        list interface {
          description "Interface options for MLD";
          key name;
          ordered-by user;
          leaf name {
            type "jt:interface-name";
            description "Interface name";
          }
          leaf multicast-router-interface {
            type empty;
            description "Enabling multicast-router-interface on the interface";
          }
          leaf immediate-leave {
            type empty;
            description "Enable immediate group leave on interfaces";
          }
          leaf host-only-interface {
            type empty;
            description "Enable interfaces to be treated as host-side interfaces";
          }
          leaf group-limit {
            type uint16;
            description "Maximum number of groups an interface can join";
          }
          container static {
            description "Static group or source membership";
            list group {
              description "IP multicast group address";
              key name;
              ordered-by user;
              leaf name {
                type "jt:ipv6addr";
                description "IP multicast group address";
              }
              list source {
                description "IP multicast source address";
                key name;
                ordered-by user;
                leaf name {
                  type "jt:ipv6addr";
                  description "Source address of IP multicast data";
                }
              }
            }
          }
        }
      }
    }
    container traceoptions {
      description "Trace options for MLD Snooping";
      container file {
        description "Trace file options";
        leaf filename {
          type string {
            length "1 .. 1024";
          }
          description "Name of file in which to write trace information";
        }
        leaf replace {
          type empty;
          description "Replace trace file rather than appending to it";
          status deprecated;
        }
        leaf size {
          type string;
          description "Maximum trace file size";
        }
        leaf files {
          type uint32 {
            range "2 .. 1000";
          }
          default "10";
          description "Maximum number of trace files";
        }
        leaf no-stamp {
          type empty;
          description "Do not timestamp trace file";
          status deprecated;
        }
        choice world-readable-choice {
          leaf world-readable {
            type empty;
            description "Allow any user to read the log file";
          }
          leaf no-world-readable {
            type empty;
            description "Don't allow any user to read the log file";
          }
        }
      }
      list flag {
        description "Tracing parameters";
        key name;
        ordered-by user;
        leaf name {
          type enumeration {
            enum packets {
              description "Trace all MLD packets";
            }
            enum query {
              description "Trace MLD membership query messages";
            }
            enum report {
              description "Trace membership report messages";
            }
            enum leave {
              description "Trace leave group messages (MLDv2 only)";
            }
            enum group {
              description "Trace group operations";
            }
            enum client-notification {
              description "Trace notifications";
            }
            enum host-notification {
              description "Trace host notifications";
            }
            enum route {
              description "Trace routing information";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
        leaf send {
          type empty;
          description "Trace transmitted packets";
        }
        leaf receive {
          type empty;
          description "Trace received packets";
        }
        leaf detail {
          type empty;
          description "Trace detailed information";
        }
        leaf disable {
          type empty;
          description "Disable this trace flag";
        }
      }
    }
    leaf query-interval {
      type uint32 {
        range "1 .. 1024";
      }
      default "125";
      description "When to send host query messages";
      units seconds;
    }
    leaf query-response-interval {
      type string;
      default "10";
      description "How long to wait for a host query response";
      units seconds;
    }
    leaf query-last-member-interval {
      type string;
      default "1";
      description "When to send group query messages";
      units seconds;
    }
    leaf robust-count {
      type uint32 {
        range "2 .. 10";
      }
      default "2";
      description "Expected packet loss on a subnet";
    }
    leaf immediate-leave {
      type empty;
      description "Enable immediate group leave on interfaces";
    }
    leaf evpn-ssm-reports-only {
      type empty;
      description "Accept and process only <s,g> reports of SSM groups";
    }
    leaf version {
      type uint8 {
        range "1 .. 2";
      }
      description "Set MLD snooping version number";
    }
    container proxy {
      description "Enable proxy mode";
      leaf source-address {
        type "jt:ipv6addr";
        description "Source IP address to use for proxy";
      }
      leaf irb {
        type empty;
        description "Proxy IGMP reports to IRB";
      }
    }
    list interface {
      description "Interface options for MLD";
      key name;
      ordered-by user;
      leaf name {
        type "jt:interface-name";
        description "Interface name";
      }
      leaf multicast-router-interface {
        type empty;
        description "Enabling multicast-router-interface on the interface";
      }
      leaf immediate-leave {
        type empty;
        description "Enable immediate group leave on interfaces";
      }
      leaf host-only-interface {
        type empty;
        description "Enable interfaces to be treated as host-side interfaces";
      }
      leaf group-limit {
        type uint16 {
          range "1 .. 65535";
        }
        description "Maximum number of (source,group) per interface";
      }
      container static {
        description "Static group or source membership";
        list group {
          description "IP multicast group address";
          key name;
          ordered-by user;
          leaf name {
            type "jt:ipv6addr";
            description "IP multicast group address";
          }
          list source {
            description "IP multicast source address";
            key name;
            ordered-by user;
            leaf name {
              type "jt:ipv6addr";
              description "Source address of IP multicast data";
            }
          }
        }
      }
    }
  }
  grouping juniper-protocols-amt {
    container traceoptions {
      description "Trace options for AMT";
      container file {
        description "Trace file options";
        leaf filename {
          type string {
            length "1 .. 1024";
          }
          description "Name of file in which to write trace information";
        }
        leaf replace {
          type empty;
          description "Replace trace file rather than appending to it";
          status deprecated;
        }
        leaf size {
          type string;
          description "Maximum trace file size";
        }
        leaf files {
          type uint32 {
            range "2 .. 1000";
          }
          default "10";
          description "Maximum number of trace files";
        }
        leaf no-stamp {
          type empty;
          description "Do not timestamp trace file";
          status deprecated;
        }
        choice world-readable-choice {
          leaf world-readable {
            type empty;
            description "Allow any user to read the log file";
          }
          leaf no-world-readable {
            type empty;
            description "Don't allow any user to read the log file";
          }
        }
      }
      list flag {
        description "Tracing parameters";
        key name;
        ordered-by user;
        leaf name {
          type enumeration {
            enum packets {
              description "Trace all AMT packets";
            }
            enum errors {
              description "Trace all error messages";
            }
            enum tunnels {
              description "Trace all AMT tunnel messages";
            }
            enum route {
              description "Trace routing information";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
        leaf send {
          type empty;
          description "Trace transmitted packets";
        }
        leaf receive {
          type empty;
          description "Trace received packets";
        }
        leaf detail {
          type empty;
          description "Trace detailed information";
        }
        leaf disable {
          type empty;
          description "Disable this trace flag";
        }
      }
    }
    container relay {
      description "AMT relay";
      presence "enable relay";
      uses juniper-protocols-amt-relay;
    }
  }
  grouping juniper-protocols-amt-relay {
    container family {
      description "Protocol family";
      presence "enable family";
      container inet {
        presence "enable inet";
        leaf anycast-prefix {
          type "jt:ipv4prefix";
          description "IPv4 anycast prefix";
        }
        leaf local-address {
          type "jt:ipv4addr";
          description "IPv4 local address";
        }
      }
    }
    leaf secret-key-timeout {
      type uint32 {
        range "5 .. 1440";
      }
      description "Time interval for the secret key to expire";
      units minutes;
    }
    leaf tunnel-limit {
      type uint32;
      description "Number of AMT tunnels";
    }
    leaf unicast-stream-limit {
      type uint32;
      description "Maximum number of AMT unicast streams(s,g,intf)";
    }
    leaf accounting {
      type empty;
      description "Enable AMT accounting";
    }
    leaf-list tunnel-devices {
      type "jt:interface-device";
      description "Tunnel devices to be used for creating ud interfaces";
      ordered-by user;
    }
  }
  grouping juniper-protocols-ancp {
    container traceoptions {
      description "Trace options for ANCP";
      leaf no-remote-trace {
        type empty;
        description "Disable remote tracing";
      }
      container file {
        description "Trace file information";
        leaf filename {
          type string {
            length "1 .. 1024";
          }
          description "Name of file in which to write trace information";
        }
        leaf size {
          type string;
          description "Maximum trace file size";
        }
        leaf files {
          type uint32 {
            range "2 .. 1000";
          }
          default "3";
          description "Maximum number of trace files";
        }
        choice world-readable-choice {
          leaf world-readable {
            type empty;
            description "Allow any user to read the log file";
          }
          leaf no-world-readable {
            type empty;
            description "Don't allow any user to read the log file";
          }
        }
        leaf match {
          type "jt:regular-expression";
          description "Regular expression for lines to be logged";
        }
      }
      leaf level {
        type enumeration {
          enum error {
            description "Match error conditions";
          }
          enum warning {
            description "Match warning messages";
          }
          enum notice {
            description "Match conditions that should be handled specially";
          }
          enum info {
            description "Match informational messages";
          }
          enum verbose {
            description "Match verbose messages";
          }
          enum all {
            description "Match all levels";
          }
        }
        default "error";
        description "Level of debugging output";
      }
      list flag {
        description "Tracing parameters";
        key name;
        ordered-by user;
        leaf name {
          type enumeration {
            enum config {
              description "Trace config events";
            }
            enum cos {
              description "Trace CoS events";
            }
            enum routing-socket {
              description "Trace routing-socket events";
            }
            enum packet {
              description "Trace ANCP packet Transmit/Receive";
            }
            enum protocol {
              description "Trace protocol events";
            }
            enum process {
              description "Trace process internals";
            }
            enum startup {
              description "Trace ANCP startup events/flow";
            }
            enum session {
              description "Trace connection events/sessions";
            }
            enum general {
              description "Trace general flow";
            }
            enum restart {
              description "Trace process restart flow";
            }
            enum subscriber {
              description "Trace subscriber events";
            }
            enum timer {
              description "Trace timer processing";
            }
            enum all {
              description "Trace everything";
            }
          }
        }
        leaf disable {
          type empty;
          description "Disable this trace flag";
        }
      }
    }
    container qos-adjust {
      description "Enable QoS adjust for interfaces and interface-sets";
      presence "enable qos-adjust";
      leaf sdsl-bytes {
        type int32 {
          range "-100 .. 100";
        }
        default "0";
        description "Set SDSL byte adjust value";
        status deprecated;
        units bytes;
      }
      leaf sdsl-overhead-adjust {
        type uint32 {
          range "80 .. 100";
        }
        default "100";
        description "Set SDSL overhead adjusted";
        status deprecated;
        units percent;
      }
      leaf vdsl-bytes {
        type int32 {
          range "-100 .. 100";
        }
        default "0";
        description "Set VDSL byte adjust value";
        status deprecated;
        units bytes;
      }
      leaf vdsl-overhead-adjust {
        type uint32 {
          range "80 .. 100";
        }
        default "100";
        description "Set VDSL overhead adjusted";
        status deprecated;
        units percent;
      }
      leaf vdsl2-bytes {
        type int32 {
          range "-100 .. 100";
        }
        default "0";
        description "Set VDSL2 byte adjust value";
        status deprecated;
        units bytes;
      }
      leaf vdsl2-overhead-adjust {
        type uint32 {
          range "80 .. 100";
        }
        default "100";
        description "Set VDSL2 overhead adjusted";
        status deprecated;
        units percent;
      }
      leaf adsl-bytes {
        type int32 {
          range "-100 .. 100";
        }
        default "0";
        description "Set ADSL byte adjust value";
        status deprecated;
        units bytes;
      }
      leaf adsl2-bytes {
        type int32 {
          range "-100 .. 100";
        }
        default "0";
        description "Set ADSL2 byte adjust value";
        status deprecated;
        units bytes;
      }
      leaf adsl2-plus-bytes {
        type int32 {
          range "-100 .. 100";
        }
        default "0";
        description "Set ADSL-PLUS byte adjust value";
        status deprecated;
        units bytes;
      }
      leaf other-bytes {
        type int32 {
          range "-100 .. 100";
        }
        default "0";
        description "Set OTHER byte adjust value";
        status deprecated;
        units bytes;
      }
      leaf other-overhead-adjust {
        type uint32 {
          range "80 .. 100";
        }
        default "100";
        description "Set OTHER overhead adjusted";
        status deprecated;
        units percent;
      }
    }
    leaf pre-ietf-mode {
      type empty;
      description "Enable backward compatibility mode";
    }
    leaf maximum-discovery-table-entries {
      type uint32 {
        range "1 .. 100000";
      }
      description "Maximum number of discovery table entries per neighbor";
    }
    leaf adjacency-timer {
      type uint32 {
        range "1 .. 25";
      }
      description "Set adjacency timer in seconds";
    }
    leaf maximum-helper-restart-time {
      type uint32 {
        range "45 .. 600";
      }
      description "Set maximum helper restart timer";
      units seconds;
    }
    leaf qos-adjust-adsl {
      type uint32 {
        range "0 .. 100";
      }
      default "100";
      description "Set ADSL QoS adjustment factor";
      status deprecated;
      units percent;
    }
    leaf qos-adjust-adsl2 {
      type uint32 {
        range "0 .. 100";
      }
      default "100";
      description "Set ADSL2 QoS adjustment factor";
      status deprecated;
      units percent;
    }
    leaf qos-adjust-adsl2-plus {
      type uint32 {
        range "0 .. 100";
      }
      default "100";
      description "Set ADSL2+ QoS adjustment factor";
      status deprecated;
      units percent;
    }
    leaf qos-adjust-vdsl {
      type uint32 {
        range "0 .. 100";
      }
      default "100";
      description "Set VDSL QoS adjustment factor";
      status deprecated;
      units percent;
    }
    leaf qos-adjust-vdsl2 {
      type uint32 {
        range "0 .. 100";
      }
      default "100";
      description "Set VDSL2 QoS adjustment factor";
      status deprecated;
      units percent;
    }
    leaf qos-adjust-sdsl {
      type uint32 {
        range "0 .. 100";
      }
      default "100";
      description "Set SDSL QoS adjustment factor";
      status deprecated;
      units percent;
    }
    leaf qos-adjust-other {
      type uint32 {
        range "0 .. 100";
      }
      default "100";
      description "Set OTHER QoS adjustment factor";
      status deprecated;
      units percent;
    }
    leaf gsmp-syn-wait {
      type empty;
      description "Enable partition ID learning";
    }
    leaf gsmp-syn-timeout {
      type uint32 {
        range "1 .. 60";
      }
      default "30";
      description "Set partition ID learning timeout";
      units seconds;
    }
    leaf adjacency-loss-hold-time {
      type uint32 {
        range "0 .. 1800";
      }
      default "0";
      description "Audit duration upon adjacency loss";
      units seconds;
    }
    container interfaces {
      description "ANCP interface config options";
      list interface-set {
        description "ANCP interface-set specific options";
        key name;
        leaf name {
          type string;
          description "Name of the interface set";
        }
        leaf access-identifier {
          type string;
          description "Subscriber specific access identifier information";
        }
        leaf neighbor {
          type "jt:ipaddr";
          description "Neighbor IP address";
          status deprecated;
        }
      }
      list interface {
        key name;
        uses ancp_interfaces_type;
      }
    }
    list neighbor {
      description "ANCP neighbor config options";
      key name;
      leaf name {
        type "jt:ipaddr";
        description "IP address of neighbor";
      }
      leaf discovery-mode {
        type empty;
        description "Enable topology discovery";
        status deprecated;
      }
      choice ietf-mode-option {
        case case_1 {
          leaf pre-ietf-mode {
            type empty;
            description "Enable backward compatibility mode";
          }
        }
        case case_2 {
          leaf ietf-mode {
            type empty;
            description "Enable IETF mode";
          }
        }
      }
      leaf adjacency-timer {
        type uint32 {
          range "1 .. 25";
        }
        description "Set adjacency timer in seconds";
      }
      leaf maximum-discovery-table-entries {
        type uint32 {
          range "1 .. 100000";
        }
        description "Maximum number of discovery table entries";
      }
      container auto-configure-trigger {
        description "Auto-configure trigger support";
        presence "enable auto-configure-trigger";
        leaf interface {
          type "jt:interface-device";
        }
      }
      leaf adjacency-loss-hold-time {
        type uint32 {
          range "0 .. 1800";
        }
        description "Audit duration upon adjacency loss";
        units seconds;
      }
    }
  }
  grouping ancp_interfaces_type {
    description "Physical interface";
    leaf name {
      type "jt:interface-name";
    }
    leaf access-identifier {
      type string;
      description "Subscriber specific access identifier information";
    }
    leaf neighbor {
      type "jt:ipaddr";
      description "Neighbor IP address";
      status deprecated;
    }
    leaf overhead-accounting {
      type empty;
      description "Enable overhead accounting on per ACI basis";
      status deprecated;
    }
  }
  grouping juniper-protocols-bgp {
    container path-selection {
      description "Configure path selection strategy";
      leaf l2vpn-use-bgp-rules {
        type empty;
        description "Use standard BGP rules during L2VPN path selection";
      }
      leaf cisco-non-deterministic {
        type empty;
        description "Use Cisco IOS nondeterministic path selection algorithm";
      }
      leaf always-compare-med {
        type empty;
        description "Always compare MED values, regardless of neighbor AS";
      }
      container med-plus-igp {
        description "Add IGP cost to next-hop to MED before comparing MED values";
        presence "enable med-plus-igp";
        leaf med-multiplier {
          type uint16 {
            range "1 .. 1000";
          }
          default "1";
          description "Multiplier for MED";
        }
        leaf igp-multiplier {
          type uint16 {
            range "1 .. 1000";
          }
          default "1";
          description "Multiplier for IGP cost to next-hop";
        }
      }
      leaf external-router-id {
        type empty;
        description "Compare router ID on BGP externals";
      }
      leaf as-path-ignore {
        type empty;
        description "Ignore AS path comparison during path selection";
      }
    }
    list group {
      description "Define a peer group";
      key name;
      ordered-by user;
      leaf name {
        type string;
        description "Group name";
      }
      leaf type {
        type enumeration {
          enum internal {
            description "IBGP group";
          }
          enum external {
            description "EBGP group";
          }
        }
        description "Type of peer group";
      }
      leaf description {
        type string {
          length "1 .. 255";
        }
        description "Text description";
      }
      leaf local-address {
        type "jt:ipaddr";
        description "Address of local end of BGP session";
      }
      leaf hold-time {
        type uint32 {
          range "0 .. 65535";
        }
        description "Hold time used when negotiating with a peer";
      }
      container family {
        description "Protocol family for NLRIs in updates";
        container inet-vpn {
          description "IPv4 Layer 3 VPN NLRI parameters";
          container unicast {
            description "Include unicast NLRI";
            presence "enable unicast";
            uses bgp-afi-l3vpn;
          }
        }
        container inet6-vpn {
          description "IPv6 Layer 3 VPN NLRI parameters";
          container unicast {
            description "Include unicast NLRI";
            presence "enable unicast";
            uses bgp-afi-l3vpn;
          }
        }
        container evpn {
          description "EVPN NLRI parameters";
          container signaling {
            description "Include EVPN signaling NLRI";
            presence "enable signaling";
          }
        }
        container route-target {
          description "Route target NLRI used for VPN route filtering";
          presence "enable route-target";
        }
      }
      leaf authentication-key {
        type string {
          length "1 .. 126";
        }
        description "MD5 authentication key";
      }
      leaf authentication-algorithm {
        type enumeration {
          enum md5 {
            description "Message Digest 5";
          }
          enum hmac-sha-1-96 {
            description "Hash-based Message Authentication Code (SHA1) (96 bits)";
          }
          enum aes-128-cmac-96 {
            description "Cipher-based Message Authentication Code (AES128) (96 bits)";
          }
          enum ao {
            description "TCP Authentication Option";
          }
        }
        description "Authentication algorithm name";
      }
      leaf tcpao-auth-mismatch {
        type enumeration {
          enum allow-without-tcpao {
            description "Allow the connection establishment without TCP-AO";
          }
        }
        description "Continue without TCP-AO if any one TCP endpoint does not have TCP-AO configured";
      }
      leaf authentication-key-chain {
        type string {
          length "1 .. 128";
        }
        description "Key chain name";
      }
      leaf-list export {
        type "jt:policy-algebra";
        description "Export policy";
        ordered-by user;
      }
      leaf tcp-mss {
        type uint32 {
          range "1 .. 4096";
        }
        description "Maximum TCP segment size";
      }
      list neighbor {
        description "Configure a neighbor";
        key name;
        ordered-by user;
        leaf name {
          type "jt:ipaddr-scoped";
        }
        leaf description {
          type string {
            length "1 .. 255";
          }
          description "Text description";
        }
        leaf passive {
          type empty;
          description "Do not send open messages to a peer";
        }
      }
    }
    leaf log-updown {
      type empty;
      description "Log a message for peer state transitions";
    }
  }
  grouping bgp-af-gr {
    container long-lived {
      description "Long-lived graceful restart options";
      container restarter {
        description "Long-lived graceful restart restarter options";
        choice enable-disable {
          case case_1 {
            leaf disable {
              type empty;
              description "Disable restarter functionality";
            }
          }
        }
        leaf stale-time {
          type string;
          description "Stale time in seconds or dhms notation (1..16777215)";
        }
      }
      container extended-route-retention {
        description "Extended route retention (LLGR-helper extended) options";
        choice enable-disable {
          case case_1 {
            leaf disable {
              type empty;
              description "Disable extended-route-retention (LLGR-helper) functionality";
            }
          }
        }
        leaf retention-time {
          type string;
          description "Retention time in seconds or dhms notation (1..16777215)";
        }
        leaf-list retention-policy {
          type "jt:policy-algebra";
          description "Retention policy for Extended Route Retention";
          ordered-by user;
        }
      }
    }
    leaf forwarding-state-bit {
      type enumeration {
        enum set {
          description "Always set";
        }
        enum from-fib {
          description "Use state of associated FIB(s)";
        }
      }
      description "Control forwarding-state flag negotiation";
    }
  }
  grouping bgp-afi-default {
    container prefix-limit {
      description "Limit maximum number of prefixes from a peer";
      uses bgpaf-prefix-limit;
    }
    container accepted-prefix-limit {
      description "Limit maximum number of prefixes accepted from a peer";
      uses bgpaf-accepted-prefix-limit;
    }
    container rib-group {
      description "Routing table group";
      uses rib_group_inet_type;
    }
    container add-path {
      description "Advertise multiple paths to peer";
      uses apath-options;
    }
    container aigp {
      description "Allow sending and receiving of AIGP attribute";
      presence "enable aigp";
      uses bgpaf-aigp-options;
    }
    leaf damping {
      type empty;
      description "Enable route flap damping";
    }
    leaf local-ipv4-address {
      type "jt:ipv4addr";
      description "Local IPv4 address";
    }
    container loops {
      description "Allow local AS in received AS paths";
      uses bgpaf-loops;
    }
    container delay-route-advertisements {
      description "Delay route updates for this family until FIB-sync";
      presence "enable delay-route-advertisements";
      leaf always-wait-for-krt-drain {
        type empty;
        description "Wait for KRT-queue drain for more-specific prefixes";
      }
      container minimum-delay {
        description "Minimum-delay to ensure KRT sees the route flash";
        leaf routing-uptime {
          type uint32 {
            range "1 .. 36000";
          }
          description "Min delay(sec) advertisement after RPD start";
        }
        leaf inbound-convergence {
          type uint32 {
            range "1 .. 36000";
          }
          description "Min delay(sec) advertisement after source-peer sent all routes";
        }
      }
      container maximum-delay {
        description "Maximum delay deferring routes";
        leaf route-age {
          type uint32 {
            range "1 .. 36000";
          }
          description "Max delay(sec) advertisement route age";
        }
        leaf routing-uptime {
          type uint32 {
            range "1 .. 36000";
          }
          description "Max delay(sec) advertisement after RPD start";
        }
      }
    }
    container nexthop-resolution {
      description "Configure nexthop resolution properties";
      leaf no-resolution {
        type empty;
        description "Consider nexthop good without resolution attempt";
      }
      leaf preserve-nexthop-hierarchy {
        type empty;
        description "Attempt preserving resolved nexthop chain in forwarding";
      }
    }
    container defer-initial-multipath-build {
      description "Defer initial multipath build until EOR is received";
      presence "enable defer-initial-multipath-build";
      leaf maximum-delay {
        type uint32 {
          range "1 .. 3600";
        }
        description "Max delay(sec) multipath build after peer is up";
      }
    }
    container graceful-restart {
      description "BGP graceful restart options";
      uses bgp-af-gr;
    }
    leaf extended-nexthop {
      type empty;
      description "Extended nexthop encoding";
    }
    leaf extended-nexthop-color {
      type empty;
      description "Resolve using extended color nexthop";
    }
    leaf extended-nexthop-tunnel {
      type empty;
      description "Use BGP tunnel attribute";
    }
    leaf no-install {
      type empty;
      description "Dont install received routes in forwarding";
    }
    leaf route-age-bgp-view {
      type empty;
      description "Maintain BGP route's age based on Update messages only";
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
    leaf advertise-srv6-service {
      type empty;
      description "Advertise SRv6 service";
    }
    leaf accept-srv6-service {
      type empty;
      description "Accept SRv6 service";
    }
  }
  grouping apath-options {
    description "Number of paths to advertise";
    leaf receive {
      type empty;
      description "Receive multiple paths from peer";
    }
    container send {
      description "Send multiple paths to peer";
      presence "enable send";
      container path-selection-mode {
        description "Configure how to select add-path routes";
        choice mode {
          case case_1 {
            leaf all-paths {
              type empty;
              description "Advertise all paths allowed by path count";
            }
          }
          case case_2 {
            leaf equal-cost-paths {
              type empty;
              description "Advertise equal cost paths";
            }
          }
        }
      }
      leaf-list prefix-policy {
        type "jt:policy-algebra";
        description "Perform add-path only for prefixes that match policy";
        ordered-by user;
      }
      leaf path-count {
        type int32 {
          range "2 .. 64";
        }
        description "Number of paths to advertise";
      }
      leaf include-backup-path {
        type int32 {
          range "1 .. 2";
        }
        description "Number of backup paths to advertise";
      }
      leaf multipath {
        type empty;
        description "Include only multipath contributor routes";
      }
    }
  }
  grouping bgp-afi-flow {
    container prefix-limit {
      description "Limit maximum number of prefixes from a peer";
      uses bgpaf-prefix-limit;
    }
    container accepted-prefix-limit {
      description "Limit maximum number of prefixes accepted from a peer";
      uses bgpaf-accepted-prefix-limit;
    }
    container rib-group {
      description "Routing table group";
      uses rib_group_inet_type;
    }
    container add-path {
      description "Advertise multiple paths to peer";
      uses apath-options;
    }
    container aigp {
      description "Allow sending and receiving of AIGP attribute";
      presence "enable aigp";
      uses bgpaf-aigp-options;
    }
    leaf damping {
      type empty;
      description "Enable route flap damping";
    }
    leaf local-ipv4-address {
      type "jt:ipv4addr";
      description "Local IPv4 address";
    }
    container loops {
      description "Allow local AS in received AS paths";
      uses bgpaf-loops;
    }
    container delay-route-advertisements {
      description "Delay route updates for this family until FIB-sync";
      presence "enable delay-route-advertisements";
      leaf always-wait-for-krt-drain {
        type empty;
        description "Wait for KRT-queue drain for more-specific prefixes";
      }
      container minimum-delay {
        description "Minimum-delay to ensure KRT sees the route flash";
        leaf routing-uptime {
          type uint32 {
            range "1 .. 36000";
          }
          description "Min delay(sec) advertisement after RPD start";
        }
        leaf inbound-convergence {
          type uint32 {
            range "1 .. 36000";
          }
          description "Min delay(sec) advertisement after source-peer sent all routes";
        }
      }
      container maximum-delay {
        description "Maximum delay deferring routes";
        leaf route-age {
          type uint32 {
            range "1 .. 36000";
          }
          description "Max delay(sec) advertisement route age";
        }
        leaf routing-uptime {
          type uint32 {
            range "1 .. 36000";
          }
          description "Max delay(sec) advertisement after RPD start";
        }
      }
    }
    container nexthop-resolution {
      description "Configure nexthop resolution properties";
      leaf no-resolution {
        type empty;
        description "Consider nexthop good without resolution attempt";
      }
      leaf preserve-nexthop-hierarchy {
        type empty;
        description "Attempt preserving resolved nexthop chain in forwarding";
      }
    }
    container defer-initial-multipath-build {
      description "Defer initial multipath build until EOR is received";
      presence "enable defer-initial-multipath-build";
      leaf maximum-delay {
        type uint32 {
          range "1 .. 3600";
        }
        description "Max delay(sec) multipath build after peer is up";
      }
    }
    container graceful-restart {
      description "BGP graceful restart options";
      uses bgp-af-gr;
    }
    leaf extended-nexthop {
      type empty;
      description "Extended nexthop encoding";
    }
    leaf extended-nexthop-color {
      type empty;
      description "Resolve using extended color nexthop";
    }
    leaf extended-nexthop-tunnel {
      type empty;
      description "Use BGP tunnel attribute";
    }
    leaf no-install {
      type empty;
      description "Dont install received routes in forwarding";
    }
    leaf route-age-bgp-view {
      type empty;
      description "Maintain BGP route's age based on Update messages only";
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
    leaf advertise-srv6-service {
      type empty;
      description "Advertise SRv6 service";
    }
    leaf accept-srv6-service {
      type empty;
      description "Accept SRv6 service";
    }
    leaf-list no-validate {
      type "jt:policy-algebra";
      description "Bypass validation procedure for routes that match policy";
      ordered-by user;
    }
    leaf strip-nexthop {
      type empty;
      description "Strip the next-hop from the outgoing flow update";
    }
    leaf allow-policy-add-nexthop {
      type empty;
      description "Allow policy to add nexthop to a route without nexthop";
      status deprecated;
    }
  }
  grouping bgp-afi-flow-with-redirect-ip-action {
    container prefix-limit {
      description "Limit maximum number of prefixes from a peer";
      uses bgpaf-prefix-limit;
    }
    container accepted-prefix-limit {
      description "Limit maximum number of prefixes accepted from a peer";
      uses bgpaf-accepted-prefix-limit;
    }
    container rib-group {
      description "Routing table group";
      uses rib_group_inet_type;
    }
    container add-path {
      description "Advertise multiple paths to peer";
      uses apath-options;
    }
    container aigp {
      description "Allow sending and receiving of AIGP attribute";
      presence "enable aigp";
      uses bgpaf-aigp-options;
    }
    leaf damping {
      type empty;
      description "Enable route flap damping";
    }
    leaf local-ipv4-address {
      type "jt:ipv4addr";
      description "Local IPv4 address";
    }
    container loops {
      description "Allow local AS in received AS paths";
      uses bgpaf-loops;
    }
    container delay-route-advertisements {
      description "Delay route updates for this family until FIB-sync";
      presence "enable delay-route-advertisements";
      leaf always-wait-for-krt-drain {
        type empty;
        description "Wait for KRT-queue drain for more-specific prefixes";
      }
      container minimum-delay {
        description "Minimum-delay to ensure KRT sees the route flash";
        leaf routing-uptime {
          type uint32 {
            range "1 .. 36000";
          }
          description "Min delay(sec) advertisement after RPD start";
        }
        leaf inbound-convergence {
          type uint32 {
            range "1 .. 36000";
          }
          description "Min delay(sec) advertisement after source-peer sent all routes";
        }
      }
      container maximum-delay {
        description "Maximum delay deferring routes";
        leaf route-age {
          type uint32 {
            range "1 .. 36000";
          }
          description "Max delay(sec) advertisement route age";
        }
        leaf routing-uptime {
          type uint32 {
            range "1 .. 36000";
          }
          description "Max delay(sec) advertisement after RPD start";
        }
      }
    }
    container nexthop-resolution {
      description "Configure nexthop resolution properties";
      leaf no-resolution {
        type empty;
        description "Consider nexthop good without resolution attempt";
      }
      leaf preserve-nexthop-hierarchy {
        type empty;
        description "Attempt preserving resolved nexthop chain in forwarding";
      }
    }
    container defer-initial-multipath-build {
      description "Defer initial multipath build until EOR is received";
      presence "enable defer-initial-multipath-build";
      leaf maximum-delay {
        type uint32 {
          range "1 .. 3600";
        }
        description "Max delay(sec) multipath build after peer is up";
      }
    }
    container graceful-restart {
      description "BGP graceful restart options";
      uses bgp-af-gr;
    }
    leaf extended-nexthop {
      type empty;
      description "Extended nexthop encoding";
    }
    leaf extended-nexthop-color {
      type empty;
      description "Resolve using extended color nexthop";
    }
    leaf extended-nexthop-tunnel {
      type empty;
      description "Use BGP tunnel attribute";
    }
    leaf no-install {
      type empty;
      description "Dont install received routes in forwarding";
    }
    leaf route-age-bgp-view {
      type empty;
      description "Maintain BGP route's age based on Update messages only";
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
    leaf advertise-srv6-service {
      type empty;
      description "Advertise SRv6 service";
    }
    leaf accept-srv6-service {
      type empty;
      description "Accept SRv6 service";
    }
    leaf-list no-validate {
      type "jt:policy-algebra";
      description "Bypass validation procedure for routes that match policy";
      ordered-by user;
    }
    leaf strip-nexthop {
      type empty;
      description "Strip the next-hop from the outgoing flow update";
    }
    container legacy-redirect-ip-action {
      description "Configure legacy redirect to IP support";
      presence "enable legacy-redirect-ip-action";
      leaf receive {
        type empty;
        description "Accept legacy encoded redirect-to-ip action attribute";
      }
      leaf send {
        type empty;
        description "Advertise Redirect action as legacy redirect attribute";
      }
    }
    leaf secondary-independent-resolution {
      type empty;
      description "Resolve FLOW routes in VRF table independent of VPN FLOW route";
    }
  }
  grouping bgp-afi-inet-transport {
    container prefix-limit {
      description "Limit maximum number of prefixes from a peer";
      uses bgpaf-prefix-limit;
    }
    container accepted-prefix-limit {
      description "Limit maximum number of prefixes accepted from a peer";
      uses bgpaf-accepted-prefix-limit;
    }
    container rib-group {
      description "Routing table group";
      uses rib_group_inet_type;
    }
    container add-path {
      description "Advertise multiple paths to peer";
      uses apath-options;
    }
    container aigp {
      description "Allow sending and receiving of AIGP attribute";
      presence "enable aigp";
      uses bgpaf-aigp-options;
    }
    leaf damping {
      type empty;
      description "Enable route flap damping";
    }
    leaf local-ipv4-address {
      type "jt:ipv4addr";
      description "Local IPv4 address";
    }
    container loops {
      description "Allow local AS in received AS paths";
      uses bgpaf-loops;
    }
    container delay-route-advertisements {
      description "Delay route updates for this family until FIB-sync";
      presence "enable delay-route-advertisements";
      leaf always-wait-for-krt-drain {
        type empty;
        description "Wait for KRT-queue drain for more-specific prefixes";
      }
      container minimum-delay {
        description "Minimum-delay to ensure KRT sees the route flash";
        leaf routing-uptime {
          type uint32 {
            range "1 .. 36000";
          }
          description "Min delay(sec) advertisement after RPD start";
        }
        leaf inbound-convergence {
          type uint32 {
            range "1 .. 36000";
          }
          description "Min delay(sec) advertisement after source-peer sent all routes";
        }
      }
      container maximum-delay {
        description "Maximum delay deferring routes";
        leaf route-age {
          type uint32 {
            range "1 .. 36000";
          }
          description "Max delay(sec) advertisement route age";
        }
        leaf routing-uptime {
          type uint32 {
            range "1 .. 36000";
          }
          description "Max delay(sec) advertisement after RPD start";
        }
      }
    }
    container nexthop-resolution {
      description "Configure nexthop resolution properties";
      leaf no-resolution {
        type empty;
        description "Consider nexthop good without resolution attempt";
      }
      leaf preserve-nexthop-hierarchy {
        type empty;
        description "Attempt preserving resolved nexthop chain in forwarding";
      }
    }
    container defer-initial-multipath-build {
      description "Defer initial multipath build until EOR is received";
      presence "enable defer-initial-multipath-build";
      leaf maximum-delay {
        type uint32 {
          range "1 .. 3600";
        }
        description "Max delay(sec) multipath build after peer is up";
      }
    }
    container graceful-restart {
      description "BGP graceful restart options";
      uses bgp-af-gr;
    }
    leaf extended-nexthop {
      type empty;
      description "Extended nexthop encoding";
    }
    leaf extended-nexthop-color {
      type empty;
      description "Resolve using extended color nexthop";
    }
    leaf extended-nexthop-tunnel {
      type empty;
      description "Use BGP tunnel attribute";
    }
    leaf no-install {
      type empty;
      description "Dont install received routes in forwarding";
    }
    leaf route-age-bgp-view {
      type empty;
      description "Maintain BGP route's age based on Update messages only";
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
    leaf advertise-srv6-service {
      type empty;
      description "Advertise SRv6 service";
    }
    leaf accept-srv6-service {
      type empty;
      description "Accept SRv6 service";
    }
    container aggregate-label {
      description "Aggregate labels of incoming routes with the same FEC";
      presence "enable aggregate-label";
      leaf community {
        type string;
        description "Community to identify the FEC of incoming routes";
      }
    }
    leaf per-prefix-label {
      type empty;
      description "Allocate a unique label to each advertised prefix";
    }
    leaf per-group-label {
      type empty;
      description "Advertise prefixes with unique labels per group";
    }
    container traffic-statistics {
      description "Collect statistics for BGP label-switched paths";
      presence "enable traffic-statistics";
      uses bgpaf-traffic-statistics;
    }
    container protection {
      description "Compute backup path for active nexthop failure";
      presence "enable protection";
    }
  }
  grouping bgp-afi-inet6-labeled {
    container prefix-limit {
      description "Limit maximum number of prefixes from a peer";
      uses bgpaf-prefix-limit;
    }
    container accepted-prefix-limit {
      description "Limit maximum number of prefixes accepted from a peer";
      uses bgpaf-accepted-prefix-limit;
    }
    container rib-group {
      description "Routing table group";
      uses rib_group_inet_type;
    }
    container add-path {
      description "Advertise multiple paths to peer";
      uses apath-options;
    }
    container aigp {
      description "Allow sending and receiving of AIGP attribute";
      presence "enable aigp";
      uses bgpaf-aigp-options;
    }
    leaf damping {
      type empty;
      description "Enable route flap damping";
    }
    leaf local-ipv4-address {
      type "jt:ipv4addr";
      description "Local IPv4 address";
    }
    container loops {
      description "Allow local AS in received AS paths";
      uses bgpaf-loops;
    }
    container delay-route-advertisements {
      description "Delay route updates for this family until FIB-sync";
      presence "enable delay-route-advertisements";
      leaf always-wait-for-krt-drain {
        type empty;
        description "Wait for KRT-queue drain for more-specific prefixes";
      }
      container minimum-delay {
        description "Minimum-delay to ensure KRT sees the route flash";
        leaf routing-uptime {
          type uint32 {
            range "1 .. 36000";
          }
          description "Min delay(sec) advertisement after RPD start";
        }
        leaf inbound-convergence {
          type uint32 {
            range "1 .. 36000";
          }
          description "Min delay(sec) advertisement after source-peer sent all routes";
        }
      }
      container maximum-delay {
        description "Maximum delay deferring routes";
        leaf route-age {
          type uint32 {
            range "1 .. 36000";
          }
          description "Max delay(sec) advertisement route age";
        }
        leaf routing-uptime {
          type uint32 {
            range "1 .. 36000";
          }
          description "Max delay(sec) advertisement after RPD start";
        }
      }
    }
    container nexthop-resolution {
      description "Configure nexthop resolution properties";
      leaf no-resolution {
        type empty;
        description "Consider nexthop good without resolution attempt";
      }
      leaf preserve-nexthop-hierarchy {
        type empty;
        description "Attempt preserving resolved nexthop chain in forwarding";
      }
    }
    container defer-initial-multipath-build {
      description "Defer initial multipath build until EOR is received";
      presence "enable defer-initial-multipath-build";
      leaf maximum-delay {
        type uint32 {
          range "1 .. 3600";
        }
        description "Max delay(sec) multipath build after peer is up";
      }
    }
    container graceful-restart {
      description "BGP graceful restart options";
      uses bgp-af-gr;
    }
    leaf extended-nexthop {
      type empty;
      description "Extended nexthop encoding";
    }
    leaf extended-nexthop-color {
      type empty;
      description "Resolve using extended color nexthop";
    }
    leaf extended-nexthop-tunnel {
      type empty;
      description "Use BGP tunnel attribute";
    }
    leaf no-install {
      type empty;
      description "Dont install received routes in forwarding";
    }
    leaf route-age-bgp-view {
      type empty;
      description "Maintain BGP route's age based on Update messages only";
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
    leaf advertise-srv6-service {
      type empty;
      description "Advertise SRv6 service";
    }
    leaf accept-srv6-service {
      type empty;
      description "Accept SRv6 service";
    }
    container aggregate-label {
      description "Aggregate labels of incoming routes with the same FEC";
      presence "enable aggregate-label";
      leaf community {
        type string;
        description "Community to identify the FEC of incoming routes";
      }
    }
    leaf per-group-label {
      type empty;
      description "Advertise prefixes with unique labels per group";
    }
    container traffic-statistics {
      description "Collect statistics for BGP label-switched paths";
      presence "enable traffic-statistics";
      uses bgpaf-traffic-statistics;
    }
    container rib {
      description "Select table used by labeled unicast routes";
      leaf "inet6.3" {
        type empty;
        description "Use inet6.3 to exchange labeled unicast routes";
      }
    }
    container explicit-null {
      description "Advertise explicit null";
      presence "enable explicit-null";
      leaf connected-only {
        type empty;
        description "Advertise explicit null only for connected routes";
      }
    }
    container protection {
      description "Compute backup path for active nexthop failure";
      presence "enable protection";
    }
    list topology {
      description "Multi topology routing tables";
      key name;
      ordered-by user;
      leaf name {
        type string;
        description "Topology name";
      }
      leaf community {
        type string;
        description "Community to identify multi topology routes";
      }
    }
  }
  grouping bgp-afi-inet6-transport {
    container prefix-limit {
      description "Limit maximum number of prefixes from a peer";
      uses bgpaf-prefix-limit;
    }
    container accepted-prefix-limit {
      description "Limit maximum number of prefixes accepted from a peer";
      uses bgpaf-accepted-prefix-limit;
    }
    container rib-group {
      description "Routing table group";
      uses rib_group_inet_type;
    }
    container add-path {
      description "Advertise multiple paths to peer";
      uses apath-options;
    }
    container aigp {
      description "Allow sending and receiving of AIGP attribute";
      presence "enable aigp";
      uses bgpaf-aigp-options;
    }
    leaf damping {
      type empty;
      description "Enable route flap damping";
    }
    leaf local-ipv4-address {
      type "jt:ipv4addr";
      description "Local IPv4 address";
    }
    container loops {
      description "Allow local AS in received AS paths";
      uses bgpaf-loops;
    }
    container delay-route-advertisements {
      description "Delay route updates for this family until FIB-sync";
      presence "enable delay-route-advertisements";
      leaf always-wait-for-krt-drain {
        type empty;
        description "Wait for KRT-queue drain for more-specific prefixes";
      }
      container minimum-delay {
        description "Minimum-delay to ensure KRT sees the route flash";
        leaf routing-uptime {
          type uint32 {
            range "1 .. 36000";
          }
          description "Min delay(sec) advertisement after RPD start";
        }
        leaf inbound-convergence {
          type uint32 {
            range "1 .. 36000";
          }
          description "Min delay(sec) advertisement after source-peer sent all routes";
        }
      }
      container maximum-delay {
        description "Maximum delay deferring routes";
        leaf route-age {
          type uint32 {
            range "1 .. 36000";
          }
          description "Max delay(sec) advertisement route age";
        }
        leaf routing-uptime {
          type uint32 {
            range "1 .. 36000";
          }
          description "Max delay(sec) advertisement after RPD start";
        }
      }
    }
    container nexthop-resolution {
      description "Configure nexthop resolution properties";
      leaf no-resolution {
        type empty;
        description "Consider nexthop good without resolution attempt";
      }
      leaf preserve-nexthop-hierarchy {
        type empty;
        description "Attempt preserving resolved nexthop chain in forwarding";
      }
    }
    container defer-initial-multipath-build {
      description "Defer initial multipath build until EOR is received";
      presence "enable defer-initial-multipath-build";
      leaf maximum-delay {
        type uint32 {
          range "1 .. 3600";
        }
        description "Max delay(sec) multipath build after peer is up";
      }
    }
    container graceful-restart {
      description "BGP graceful restart options";
      uses bgp-af-gr;
    }
    leaf extended-nexthop {
      type empty;
      description "Extended nexthop encoding";
    }
    leaf extended-nexthop-color {
      type empty;
      description "Resolve using extended color nexthop";
    }
    leaf extended-nexthop-tunnel {
      type empty;
      description "Use BGP tunnel attribute";
    }
    leaf no-install {
      type empty;
      description "Dont install received routes in forwarding";
    }
    leaf route-age-bgp-view {
      type empty;
      description "Maintain BGP route's age based on Update messages only";
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
    leaf advertise-srv6-service {
      type empty;
      description "Advertise SRv6 service";
    }
    leaf accept-srv6-service {
      type empty;
      description "Accept SRv6 service";
    }
    container aggregate-label {
      description "Aggregate labels of incoming routes with the same FEC";
      presence "enable aggregate-label";
      leaf community {
        type string;
        description "Community to identify the FEC of incoming routes";
      }
    }
    leaf per-prefix-label {
      type empty;
      description "Allocate a unique label to each advertised prefix";
    }
    leaf per-group-label {
      type empty;
      description "Advertise prefixes with unique labels per group";
    }
    container traffic-statistics {
      description "Collect statistics for BGP label-switched paths";
      presence "enable traffic-statistics";
      uses bgpaf-traffic-statistics;
    }
    container lu-export {
      description "Install Classful Transport routes in inet6.3";
      presence "enable lu-export";
    }
    container protection {
      description "Compute backup path for active nexthop failure";
      presence "enable protection";
    }
  }
  grouping bgp-afi-l2vpn {
    container prefix-limit {
      description "Limit maximum number of prefixes from a peer";
      uses bgpaf-prefix-limit;
    }
    container accepted-prefix-limit {
      description "Limit maximum number of prefixes accepted from a peer";
      uses bgpaf-accepted-prefix-limit;
    }
    container rib-group {
      description "Routing table group";
      uses rib_group_inet_type;
    }
    container add-path {
      description "Advertise multiple paths to peer";
      uses apath-options;
    }
    container aigp {
      description "Allow sending and receiving of AIGP attribute";
      presence "enable aigp";
      uses bgpaf-aigp-options;
    }
    leaf damping {
      type empty;
      description "Enable route flap damping";
    }
    leaf local-ipv4-address {
      type "jt:ipv4addr";
      description "Local IPv4 address";
    }
    container loops {
      description "Allow local AS in received AS paths";
      uses bgpaf-loops;
    }
    container delay-route-advertisements {
      description "Delay route updates for this family until FIB-sync";
      presence "enable delay-route-advertisements";
      leaf always-wait-for-krt-drain {
        type empty;
        description "Wait for KRT-queue drain for more-specific prefixes";
      }
      container minimum-delay {
        description "Minimum-delay to ensure KRT sees the route flash";
        leaf routing-uptime {
          type uint32 {
            range "1 .. 36000";
          }
          description "Min delay(sec) advertisement after RPD start";
        }
        leaf inbound-convergence {
          type uint32 {
            range "1 .. 36000";
          }
          description "Min delay(sec) advertisement after source-peer sent all routes";
        }
      }
      container maximum-delay {
        description "Maximum delay deferring routes";
        leaf route-age {
          type uint32 {
            range "1 .. 36000";
          }
          description "Max delay(sec) advertisement route age";
        }
        leaf routing-uptime {
          type uint32 {
            range "1 .. 36000";
          }
          description "Max delay(sec) advertisement after RPD start";
        }
      }
    }
    container nexthop-resolution {
      description "Configure nexthop resolution properties";
      leaf no-resolution {
        type empty;
        description "Consider nexthop good without resolution attempt";
      }
      leaf preserve-nexthop-hierarchy {
        type empty;
        description "Attempt preserving resolved nexthop chain in forwarding";
      }
    }
    container defer-initial-multipath-build {
      description "Defer initial multipath build until EOR is received";
      presence "enable defer-initial-multipath-build";
      leaf maximum-delay {
        type uint32 {
          range "1 .. 3600";
        }
        description "Max delay(sec) multipath build after peer is up";
      }
    }
    container graceful-restart {
      description "BGP graceful restart options";
      uses bgp-af-gr;
    }
    leaf extended-nexthop {
      type empty;
      description "Extended nexthop encoding";
    }
    leaf extended-nexthop-color {
      type empty;
      description "Resolve using extended color nexthop";
    }
    leaf extended-nexthop-tunnel {
      type empty;
      description "Use BGP tunnel attribute";
    }
    leaf no-install {
      type empty;
      description "Dont install received routes in forwarding";
    }
    leaf route-age-bgp-view {
      type empty;
      description "Maintain BGP route's age based on Update messages only";
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
    leaf advertise-srv6-service {
      type empty;
      description "Advertise SRv6 service";
    }
    leaf accept-srv6-service {
      type empty;
      description "Accept SRv6 service";
    }
    container egress-protection {
      description "Egress router protection";
      presence "enable egress-protection";
      container context-identifier {
        description "Context identifier";
        leaf context-id {
          type "jt:ipv4addr";
          description "IP address";
        }
      }
      leaf-list keep-import {
        type "jt:policy-algebra";
        description "Import policy";
        ordered-by user;
      }
    }
  }
  grouping bgp-afi-l3vpn {
    container prefix-limit {
      description "Limit maximum number of prefixes from a peer";
      uses bgpaf-prefix-limit;
    }
    container accepted-prefix-limit {
      description "Limit maximum number of prefixes accepted from a peer";
      uses bgpaf-accepted-prefix-limit;
    }
    container rib-group {
      description "Routing table group";
      uses rib_group_inet_type;
    }
    container add-path {
      description "Advertise multiple paths to peer";
      uses apath-options;
    }
    container aigp {
      description "Allow sending and receiving of AIGP attribute";
      presence "enable aigp";
      uses bgpaf-aigp-options;
    }
    leaf damping {
      type empty;
      description "Enable route flap damping";
    }
    leaf local-ipv4-address {
      type "jt:ipv4addr";
      description "Local IPv4 address";
    }
    container loops {
      description "Allow local AS in received AS paths";
      uses bgpaf-loops;
    }
    container delay-route-advertisements {
      description "Delay route updates for this family until FIB-sync";
      presence "enable delay-route-advertisements";
      leaf always-wait-for-krt-drain {
        type empty;
        description "Wait for KRT-queue drain for more-specific prefixes";
      }
      container minimum-delay {
        description "Minimum-delay to ensure KRT sees the route flash";
        leaf routing-uptime {
          type uint32 {
            range "1 .. 36000";
          }
          description "Min delay(sec) advertisement after RPD start";
        }
        leaf inbound-convergence {
          type uint32 {
            range "1 .. 36000";
          }
          description "Min delay(sec) advertisement after source-peer sent all routes";
        }
      }
      container maximum-delay {
        description "Maximum delay deferring routes";
        leaf route-age {
          type uint32 {
            range "1 .. 36000";
          }
          description "Max delay(sec) advertisement route age";
        }
        leaf routing-uptime {
          type uint32 {
            range "1 .. 36000";
          }
          description "Max delay(sec) advertisement after RPD start";
        }
      }
    }
    container nexthop-resolution {
      description "Configure nexthop resolution properties";
      leaf no-resolution {
        type empty;
        description "Consider nexthop good without resolution attempt";
      }
      leaf preserve-nexthop-hierarchy {
        type empty;
        description "Attempt preserving resolved nexthop chain in forwarding";
      }
    }
    container defer-initial-multipath-build {
      description "Defer initial multipath build until EOR is received";
      presence "enable defer-initial-multipath-build";
      leaf maximum-delay {
        type uint32 {
          range "1 .. 3600";
        }
        description "Max delay(sec) multipath build after peer is up";
      }
    }
    container graceful-restart {
      description "BGP graceful restart options";
      uses bgp-af-gr;
    }
    leaf extended-nexthop {
      type empty;
      description "Extended nexthop encoding";
    }
    leaf extended-nexthop-color {
      type empty;
      description "Resolve using extended color nexthop";
    }
    leaf extended-nexthop-tunnel {
      type empty;
      description "Use BGP tunnel attribute";
    }
    leaf no-install {
      type empty;
      description "Dont install received routes in forwarding";
    }
    leaf route-age-bgp-view {
      type empty;
      description "Maintain BGP route's age based on Update messages only";
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
    leaf advertise-srv6-service {
      type empty;
      description "Advertise SRv6 service";
    }
    leaf accept-srv6-service {
      type empty;
      description "Accept SRv6 service";
    }
    container aggregate-label {
      description "Aggregate labels of incoming routes with the same FEC";
      presence "enable aggregate-label";
      leaf community {
        type string;
        description "Community to identify the FEC of incoming routes";
      }
    }
    container egress-protection {
      description "Egress router protection";
      presence "enable egress-protection";
      container context-identifier {
        description "Context identifier";
        leaf context-id {
          type "jt:ipv4addr";
          description "IP address";
        }
      }
      leaf-list keep-import {
        type "jt:policy-algebra";
        description "Import policy";
        ordered-by user;
      }
    }
    leaf accept-local-nexthop {
      type empty;
      description "Enable processing of routes with own nexthop";
    }
    leaf accept-own {
      type empty;
      description "Enable processing of routes with own originator-id or nexthop";
    }
  }
  grouping bgp-afi-labeled {
    container prefix-limit {
      description "Limit maximum number of prefixes from a peer";
      uses bgpaf-prefix-limit;
    }
    container accepted-prefix-limit {
      description "Limit maximum number of prefixes accepted from a peer";
      uses bgpaf-accepted-prefix-limit;
    }
    container rib-group {
      description "Routing table group";
      uses rib_group_inet_type;
    }
    container add-path {
      description "Advertise multiple paths to peer";
      uses apath-options;
    }
    container aigp {
      description "Allow sending and receiving of AIGP attribute";
      presence "enable aigp";
      uses bgpaf-aigp-options;
    }
    leaf damping {
      type empty;
      description "Enable route flap damping";
    }
    leaf local-ipv4-address {
      type "jt:ipv4addr";
      description "Local IPv4 address";
    }
    container loops {
      description "Allow local AS in received AS paths";
      uses bgpaf-loops;
    }
    container delay-route-advertisements {
      description "Delay route updates for this family until FIB-sync";
      presence "enable delay-route-advertisements";
      leaf always-wait-for-krt-drain {
        type empty;
        description "Wait for KRT-queue drain for more-specific prefixes";
      }
      container minimum-delay {
        description "Minimum-delay to ensure KRT sees the route flash";
        leaf routing-uptime {
          type uint32 {
            range "1 .. 36000";
          }
          description "Min delay(sec) advertisement after RPD start";
        }
        leaf inbound-convergence {
          type uint32 {
            range "1 .. 36000";
          }
          description "Min delay(sec) advertisement after source-peer sent all routes";
        }
      }
      container maximum-delay {
        description "Maximum delay deferring routes";
        leaf route-age {
          type uint32 {
            range "1 .. 36000";
          }
          description "Max delay(sec) advertisement route age";
        }
        leaf routing-uptime {
          type uint32 {
            range "1 .. 36000";
          }
          description "Max delay(sec) advertisement after RPD start";
        }
      }
    }
    container nexthop-resolution {
      description "Configure nexthop resolution properties";
      leaf no-resolution {
        type empty;
        description "Consider nexthop good without resolution attempt";
      }
      leaf preserve-nexthop-hierarchy {
        type empty;
        description "Attempt preserving resolved nexthop chain in forwarding";
      }
    }
    container defer-initial-multipath-build {
      description "Defer initial multipath build until EOR is received";
      presence "enable defer-initial-multipath-build";
      leaf maximum-delay {
        type uint32 {
          range "1 .. 3600";
        }
        description "Max delay(sec) multipath build after peer is up";
      }
    }
    container graceful-restart {
      description "BGP graceful restart options";
      uses bgp-af-gr;
    }
    leaf extended-nexthop {
      type empty;
      description "Extended nexthop encoding";
    }
    leaf extended-nexthop-color {
      type empty;
      description "Resolve using extended color nexthop";
    }
    leaf extended-nexthop-tunnel {
      type empty;
      description "Use BGP tunnel attribute";
    }
    leaf no-install {
      type empty;
      description "Dont install received routes in forwarding";
    }
    leaf route-age-bgp-view {
      type empty;
      description "Maintain BGP route's age based on Update messages only";
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
    leaf advertise-srv6-service {
      type empty;
      description "Advertise SRv6 service";
    }
    leaf accept-srv6-service {
      type empty;
      description "Accept SRv6 service";
    }
    container aggregate-label {
      description "Aggregate labels of incoming routes with the same FEC";
      presence "enable aggregate-label";
      leaf community {
        type string;
        description "Community to identify the FEC of incoming routes";
      }
    }
    leaf per-prefix-label {
      type empty;
      description "Allocate a unique label to each advertised prefix";
    }
    leaf per-group-label {
      type empty;
      description "Advertise prefixes with unique labels per group";
    }
    container traffic-statistics {
      description "Collect statistics for BGP label-switched paths";
      presence "enable traffic-statistics";
      uses bgpaf-traffic-statistics;
    }
    list topology {
      description "Multi topology routing tables";
      key name;
      ordered-by user;
      leaf name {
        type string;
        description "Topology name";
      }
      leaf community {
        type string;
        description "Community to identify multi topology routes";
      }
    }
    container rib {
      description "Select table used by labeled unicast routes";
      uses rib-inet3;
    }
    container explicit-null {
      description "Advertise explicit null";
      presence "enable explicit-null";
      leaf connected-only {
        type empty;
        description "Advertise explicit null only for connected routes";
      }
    }
    container protection {
      description "Compute backup path for active nexthop failure";
      presence "enable protection";
    }
    container egress-protection {
      description "Egress router protection";
      presence "enable egress-protection";
      container context-identifier {
        description "Context identifier";
        leaf context-id {
          type "jt:ipv4addr";
          description "IP address";
        }
      }
      leaf-list keep-import {
        type "jt:policy-algebra";
        description "Import policy";
        ordered-by user;
      }
    }
    leaf resolve-vpn {
      type empty;
      description "Install received NLRI in inet.3 also";
    }
    container entropy-label {
      description "Use entropy label for entropy label capable BGP LSPs";
      presence "enable entropy-label";
      leaf-list import {
        type "jt:policy-algebra";
        description "Policy to select BGP LSPs to use entropy label";
        ordered-by user;
      }
      leaf no-next-hop-validation {
        type empty;
        description "Don't validate next hop field against route next hop";
      }
      leaf elc-v2-compatible {
        type empty;
        description "Send and accept ELCv2 in addition to ELCv3";
      }
    }
  }
  grouping bgp-afi-srte {
    container prefix-limit {
      description "Limit maximum number of prefixes from a peer";
      uses bgpaf-prefix-limit;
    }
    container accepted-prefix-limit {
      description "Limit maximum number of prefixes accepted from a peer";
      uses bgpaf-accepted-prefix-limit;
    }
    leaf damping {
      type empty;
      description "Enable route flap damping";
    }
    container loops {
      description "Allow local AS in received AS paths";
      uses bgpaf-loops;
    }
    container graceful-restart {
      description "BGP graceful restart options";
      uses bgp-af-gr;
    }
    leaf no-install {
      type empty;
      description "Dont install received routes in forwarding";
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
  }
  grouping bgp-afi-topo {
    container prefix-limit {
      description "Limit maximum number of prefixes from a peer";
      uses bgpaf-prefix-limit;
    }
    container accepted-prefix-limit {
      description "Limit maximum number of prefixes accepted from a peer";
      uses bgpaf-accepted-prefix-limit;
    }
    container rib-group {
      description "Routing table group";
      uses rib_group_inet_type;
    }
    container add-path {
      description "Advertise multiple paths to peer";
      uses apath-options;
    }
    container aigp {
      description "Allow sending and receiving of AIGP attribute";
      presence "enable aigp";
      uses bgpaf-aigp-options;
    }
    leaf damping {
      type empty;
      description "Enable route flap damping";
    }
    leaf local-ipv4-address {
      type "jt:ipv4addr";
      description "Local IPv4 address";
    }
    container loops {
      description "Allow local AS in received AS paths";
      uses bgpaf-loops;
    }
    container delay-route-advertisements {
      description "Delay route updates for this family until FIB-sync";
      presence "enable delay-route-advertisements";
      leaf always-wait-for-krt-drain {
        type empty;
        description "Wait for KRT-queue drain for more-specific prefixes";
      }
      container minimum-delay {
        description "Minimum-delay to ensure KRT sees the route flash";
        leaf routing-uptime {
          type uint32 {
            range "1 .. 36000";
          }
          description "Min delay(sec) advertisement after RPD start";
        }
        leaf inbound-convergence {
          type uint32 {
            range "1 .. 36000";
          }
          description "Min delay(sec) advertisement after source-peer sent all routes";
        }
      }
      container maximum-delay {
        description "Maximum delay deferring routes";
        leaf route-age {
          type uint32 {
            range "1 .. 36000";
          }
          description "Max delay(sec) advertisement route age";
        }
        leaf routing-uptime {
          type uint32 {
            range "1 .. 36000";
          }
          description "Max delay(sec) advertisement after RPD start";
        }
      }
    }
    container nexthop-resolution {
      description "Configure nexthop resolution properties";
      leaf no-resolution {
        type empty;
        description "Consider nexthop good without resolution attempt";
      }
      leaf preserve-nexthop-hierarchy {
        type empty;
        description "Attempt preserving resolved nexthop chain in forwarding";
      }
    }
    container defer-initial-multipath-build {
      description "Defer initial multipath build until EOR is received";
      presence "enable defer-initial-multipath-build";
      leaf maximum-delay {
        type uint32 {
          range "1 .. 3600";
        }
        description "Max delay(sec) multipath build after peer is up";
      }
    }
    container graceful-restart {
      description "BGP graceful restart options";
      uses bgp-af-gr;
    }
    leaf extended-nexthop {
      type empty;
      description "Extended nexthop encoding";
    }
    leaf extended-nexthop-color {
      type empty;
      description "Resolve using extended color nexthop";
    }
    leaf extended-nexthop-tunnel {
      type empty;
      description "Use BGP tunnel attribute";
    }
    leaf no-install {
      type empty;
      description "Dont install received routes in forwarding";
    }
    leaf route-age-bgp-view {
      type empty;
      description "Maintain BGP route's age based on Update messages only";
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
    leaf advertise-srv6-service {
      type empty;
      description "Advertise SRv6 service";
    }
    leaf accept-srv6-service {
      type empty;
      description "Accept SRv6 service";
    }
    container protection {
      description "Compute backup path for active nexthop failure";
      presence "enable protection";
    }
    list topology {
      description "Multi topology routing tables";
      key name;
      ordered-by user;
      leaf name {
        type string;
        description "Topology name";
      }
      leaf community {
        type string;
        description "Community to identify multi topology routes";
      }
    }
  }
  grouping bgp-afi-vpn {
    container prefix-limit {
      description "Limit maximum number of prefixes from a peer";
      uses bgpaf-prefix-limit;
    }
    container accepted-prefix-limit {
      description "Limit maximum number of prefixes accepted from a peer";
      uses bgpaf-accepted-prefix-limit;
    }
    container rib-group {
      description "Routing table group";
      uses rib_group_inet_type;
    }
    container add-path {
      description "Advertise multiple paths to peer";
      uses apath-options;
    }
    container aigp {
      description "Allow sending and receiving of AIGP attribute";
      presence "enable aigp";
      uses bgpaf-aigp-options;
    }
    leaf damping {
      type empty;
      description "Enable route flap damping";
    }
    leaf local-ipv4-address {
      type "jt:ipv4addr";
      description "Local IPv4 address";
    }
    container loops {
      description "Allow local AS in received AS paths";
      uses bgpaf-loops;
    }
    container delay-route-advertisements {
      description "Delay route updates for this family until FIB-sync";
      presence "enable delay-route-advertisements";
      leaf always-wait-for-krt-drain {
        type empty;
        description "Wait for KRT-queue drain for more-specific prefixes";
      }
      container minimum-delay {
        description "Minimum-delay to ensure KRT sees the route flash";
        leaf routing-uptime {
          type uint32 {
            range "1 .. 36000";
          }
          description "Min delay(sec) advertisement after RPD start";
        }
        leaf inbound-convergence {
          type uint32 {
            range "1 .. 36000";
          }
          description "Min delay(sec) advertisement after source-peer sent all routes";
        }
      }
      container maximum-delay {
        description "Maximum delay deferring routes";
        leaf route-age {
          type uint32 {
            range "1 .. 36000";
          }
          description "Max delay(sec) advertisement route age";
        }
        leaf routing-uptime {
          type uint32 {
            range "1 .. 36000";
          }
          description "Max delay(sec) advertisement after RPD start";
        }
      }
    }
    container nexthop-resolution {
      description "Configure nexthop resolution properties";
      leaf no-resolution {
        type empty;
        description "Consider nexthop good without resolution attempt";
      }
      leaf preserve-nexthop-hierarchy {
        type empty;
        description "Attempt preserving resolved nexthop chain in forwarding";
      }
    }
    container defer-initial-multipath-build {
      description "Defer initial multipath build until EOR is received";
      presence "enable defer-initial-multipath-build";
      leaf maximum-delay {
        type uint32 {
          range "1 .. 3600";
        }
        description "Max delay(sec) multipath build after peer is up";
      }
    }
    container graceful-restart {
      description "BGP graceful restart options";
      uses bgp-af-gr;
    }
    leaf extended-nexthop {
      type empty;
      description "Extended nexthop encoding";
    }
    leaf extended-nexthop-color {
      type empty;
      description "Resolve using extended color nexthop";
    }
    leaf extended-nexthop-tunnel {
      type empty;
      description "Use BGP tunnel attribute";
    }
    leaf no-install {
      type empty;
      description "Dont install received routes in forwarding";
    }
    leaf route-age-bgp-view {
      type empty;
      description "Maintain BGP route's age based on Update messages only";
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
    leaf advertise-srv6-service {
      type empty;
      description "Advertise SRv6 service";
    }
    leaf accept-srv6-service {
      type empty;
      description "Accept SRv6 service";
    }
    container aggregate-label {
      description "Aggregate labels of incoming routes with the same FEC";
      presence "enable aggregate-label";
      leaf community {
        type string;
        description "Community to identify the FEC of incoming routes";
      }
    }
  }
  grouping bgp-afi-vpn-protection {
    container prefix-limit {
      description "Limit maximum number of prefixes from a peer";
      uses bgpaf-prefix-limit;
    }
    container accepted-prefix-limit {
      description "Limit maximum number of prefixes accepted from a peer";
      uses bgpaf-accepted-prefix-limit;
    }
    container rib-group {
      description "Routing table group";
      uses rib_group_inet_type;
    }
    container add-path {
      description "Advertise multiple paths to peer";
      uses apath-options;
    }
    container aigp {
      description "Allow sending and receiving of AIGP attribute";
      presence "enable aigp";
      uses bgpaf-aigp-options;
    }
    leaf damping {
      type empty;
      description "Enable route flap damping";
    }
    leaf local-ipv4-address {
      type "jt:ipv4addr";
      description "Local IPv4 address";
    }
    container loops {
      description "Allow local AS in received AS paths";
      uses bgpaf-loops;
    }
    container delay-route-advertisements {
      description "Delay route updates for this family until FIB-sync";
      presence "enable delay-route-advertisements";
      leaf always-wait-for-krt-drain {
        type empty;
        description "Wait for KRT-queue drain for more-specific prefixes";
      }
      container minimum-delay {
        description "Minimum-delay to ensure KRT sees the route flash";
        leaf routing-uptime {
          type uint32 {
            range "1 .. 36000";
          }
          description "Min delay(sec) advertisement after RPD start";
        }
        leaf inbound-convergence {
          type uint32 {
            range "1 .. 36000";
          }
          description "Min delay(sec) advertisement after source-peer sent all routes";
        }
      }
      container maximum-delay {
        description "Maximum delay deferring routes";
        leaf route-age {
          type uint32 {
            range "1 .. 36000";
          }
          description "Max delay(sec) advertisement route age";
        }
        leaf routing-uptime {
          type uint32 {
            range "1 .. 36000";
          }
          description "Max delay(sec) advertisement after RPD start";
        }
      }
    }
    container nexthop-resolution {
      description "Configure nexthop resolution properties";
      leaf no-resolution {
        type empty;
        description "Consider nexthop good without resolution attempt";
      }
      leaf preserve-nexthop-hierarchy {
        type empty;
        description "Attempt preserving resolved nexthop chain in forwarding";
      }
    }
    container defer-initial-multipath-build {
      description "Defer initial multipath build until EOR is received";
      presence "enable defer-initial-multipath-build";
      leaf maximum-delay {
        type uint32 {
          range "1 .. 3600";
        }
        description "Max delay(sec) multipath build after peer is up";
      }
    }
    container graceful-restart {
      description "BGP graceful restart options";
      uses bgp-af-gr;
    }
    leaf extended-nexthop {
      type empty;
      description "Extended nexthop encoding";
    }
    leaf extended-nexthop-color {
      type empty;
      description "Resolve using extended color nexthop";
    }
    leaf extended-nexthop-tunnel {
      type empty;
      description "Use BGP tunnel attribute";
    }
    leaf no-install {
      type empty;
      description "Dont install received routes in forwarding";
    }
    leaf route-age-bgp-view {
      type empty;
      description "Maintain BGP route's age based on Update messages only";
    }
    container output-queue-priority {
      description "Default output-queue to assign updates to";
      uses bgp-output-queue-priority-class;
    }
    container route-refresh-priority {
      description "Default output-queue to assign route refreshes to";
      uses bgp-output-queue-priority-class;
    }
    container withdraw-priority {
      description "Default output-queue to assign withdrawn routes to";
      uses bgp-output-queue-priority-class;
    }
    leaf advertise-srv6-service {
      type empty;
      description "Advertise SRv6 service";
    }
    leaf accept-srv6-service {
      type empty;
      description "Accept SRv6 service";
    }
    container aggregate-label {
      description "Aggregate labels of incoming routes with the same FEC";
      presence "enable aggregate-label";
      leaf community {
        type string;
        description "Community to identify the FEC of incoming routes";
      }
    }
    container egress-protection {
      description "Egress router protection";
      presence "enable egress-protection";
      container context-identifier {
        description "Context identifier";
        leaf context-id {
          type "jt:ipv4addr";
          description "IP address";
        }
      }
      leaf-list keep-import {
        type "jt:policy-algebra";
        description "Import policy";
        ordered-by user;
      }
    }
  }
  grouping bgp-output-queue-priority-class {
    choice class {
      case case_1 {
        leaf priority {
          type uint32 {
            range "1 .. 16";
          }
          description "Output queue priority; higher is better";
        }
      }
      case case_2 {
        leaf expedited {
          type empty;
          description "Expedited queue; highest priority";
        }
      }
    }
  }
  grouping bgp_filter_obj {
    description "Filter to apply to tracing";
    leaf match-on {
      type enumeration {
        enum prefix {
          description "Filter based on prefix";
        }
      }
      description "Argument on which to match";
    }
    leaf-list policy {
      type "jt:policy-algebra";
      description "Filter policy";
      ordered-by user;
    }
  }
  grouping bgpaf-accepted-prefix-limit {
    leaf maximum {
      type uint32 {
        range "1 .. 4294967295";
      }
      description "Maximum number of prefixes accepted from a peer";
    }
    container teardown {
      description "Clear peer connection on reaching limit";
      presence "enable teardown";
      leaf limit-threshold {
        type uint32 {
          range "1 .. 100";
        }
        description "Percentage of prefix-limit to start warnings";
      }
      container idle-timeout {
        description "Timeout before attempting to restart peer";
        presence "enable idle-timeout";
        choice idle-parm {
          case case_1 {
            leaf forever {
              type empty;
              description "Idle the peer until the user intervenes";
            }
          }
          case case_2 {
            leaf timeout {
              type uint32 {
                range "1 .. 2400";
              }
              description "Timeout value, in minutes, for restarting peer";
            }
          }
        }
      }
    }
    container drop-excess {
      description "Drop routes from peer on reaching limit";
      presence "enable drop-excess";
      leaf limit-threshold {
        type uint32 {
          range "1 .. 100";
        }
        description "Percentage of prefix-limit to start warnings";
      }
    }
    container hide-excess {
      description "Hide routes from peer on reaching limit";
      presence "enable hide-excess";
      leaf limit-threshold {
        type uint32 {
          range "1 .. 100";
        }
        description "Percentage of prefix-limit to start warnings";
      }
    }
  }
  grouping bgpaf-aigp-options {
    leaf disable {
      type empty;
      description "Disable sending and receiving of AIGP attribute";
    }
  }
  grouping bgpaf-loops {
    leaf loops {
      type int32 {
        range "1 .. 10";
      }
      description "AS-Path loop count";
    }
  }
  grouping bgpaf-prefix-limit {
    leaf maximum {
      type uint32 {
        range "1 .. 4294967295";
      }
      description "Maximum number of prefixes from a peer";
    }
    container teardown {
      description "Clear peer connection on reaching limit";
      presence "enable teardown";
      leaf limit-threshold {
        type uint32 {
          range "1 .. 100";
        }
        description "Percentage of prefix-limit to start warnings";
      }
      container idle-timeout {
        description "Timeout before attempting to restart peer";
        presence "enable idle-timeout";
        choice idle-parm {
          case case_1 {
            leaf forever {
              type empty;
              description "Idle the peer until the user intervenes";
            }
          }
          case case_2 {
            leaf timeout {
              type uint32 {
                range "1 .. 2400";
              }
              description "Timeout value, in minutes, for restarting peer";
            }
          }
        }
      }
    }
    container drop-excess {
      description "Drop routes from peer on reaching limit";
      presence "enable drop-excess";
      leaf limit-threshold {
        type uint32 {
          range "1 .. 100";
        }
        description "Percentage of prefix-limit to start warnings";
      }
    }
    container hide-excess {
      description "Hide routes from peer on reaching limit";
      presence "enable hide-excess";
      leaf limit-threshold {
        type uint32 {
          range "1 .. 100";
        }
        description "Percentage of prefix-limit to start warnings";
      }
    }
  }
  grouping bgpaf-traffic-statistics {
    leaf labeled-path {
      type empty;
      description "Ingress labeled path statistics";
    }
    container file {
      description "Statistics file options";
      leaf filename {
        type string {
          length "1 .. 1024";
        }
        description "Name of file in which to write trace information";
      }
      leaf replace {
        type empty;
        description "Replace trace file rather than appending to it";
        status deprecated;
      }
      leaf size {
        type string;
        description "Maximum trace file size";
      }
      leaf files {
        type uint32 {
          range "2 .. 1000";
        }
        default "10";
        description "Maximum number of trace files";
      }
      leaf no-stamp {
        type empty;
        description "Do not timestamp trace file";
        status deprecated;
      }
      choice world-readable-choice {
        leaf world-readable {
          type empty;
          description "Allow any user to read the log file";
        }
        leaf no-world-readable {
          type empty;
          description "Don't allow any user to read the log file";
        }
      }
    }
    leaf interval {
      type int32 {
        range "60 .. 65535";
      }
      description "Time to collect statistics (seconds)";
    }
  }
  grouping juniper-protocols-bgpmcast {
    description "BGP Multicast configuration";
    container traceoptions {
      description "Trace options for BGP Multicast";
      container file {
        description "Trace file options";
        leaf filename {
          type string {
            length "1 .. 1024";
          }
          description "Name of file in which to write trace information";
        }
        leaf replace {
          type empty;
          description "Replace trace file rather than appending to it";
          status deprecated;
        }
        leaf size {
          type string;
          description "Maximum trace file size";
        }
        leaf files {
          type uint32 {
            range "2 .. 1000";
          }
          default "10";
          description "Maximum number of trace files";
        }
        leaf no-stamp {
          type empty;
          description "Do not timestamp trace file";
          status deprecated;
        }
        choice world-readable-choice {
          leaf world-readable {
            type empty;
            description "Allow any user to read the log file";
          }
          leaf no-world-readable {
            type empty;
            description "Don't allow any user to read the log file";
          }
        }
      }
      list flag {
        description "Tracing parameters";
        key name;
        ordered-by user;
        leaf name {
          type enumeration {
            enum route {
              description "Trace routing information";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
        leaf send {
          type empty;
          description "Trace transmitted packets";
        }
        leaf receive {
          type empty;
          description "Trace received packets";
        }
        leaf detail {
          type empty;
          description "Trace detailed information";
        }
        leaf disable {
          type empty;
          description "Disable this trace flag";
        }
      }
    }
  }
  grouping juniper-protocols-bridge {
    container traceoptions {
      description "Trace options for Layer 2 address service";
      leaf no-remote-trace {
        type empty;
        description "Disable remote tracing";
      }
      container file {
        description "Trace file information";
        leaf filename {
          type string {
            length "1 .. 1024";
          }
          description "Name of file in which to write trace information";
        }
        leaf size {
          type string;
          description "Maximum trace file size";
        }
        leaf files {
          type uint32 {
            range "2 .. 1000";
          }
          default "3";
          description "Maximum number of trace files";
        }
        choice world-readable-choice {
          leaf world-readable {
            type empty;
            description "Allow any user to read the log file";
          }
          leaf no-world-readable {
            type empty;
            description "Don't allow any user to read the log file";
          }
        }
        leaf match {
          type "jt:regular-expression";
          description "Regular expression for lines to be logged";
        }
      }
      leaf level {
        type enumeration {
          enum error {
            description "Match error conditions";
          }
          enum warning {
            description "Match warning messages";
          }
          enum notice {
            description "Match conditions that should be handled specially";
          }
          enum info {
            description "Match informational messages";
          }
          enum verbose {
            description "Match verbose messages";
          }
          enum all {
            description "Match all levels";
          }
        }
        default "error";
        description "Level of debugging output";
      }
      list flag {
        description "Type of operation or event to include in trace";
        key name;
        ordered-by user;
        leaf name {
          type enumeration {
            enum configuration {
              description "Configuration operations";
            }
            enum routing-socket {
              description "Routing socket operations";
            }
            enum interface-device {
              description "Interface device operations";
            }
            enum interface-logical {
              description "Logical interface operations";
            }
            enum interface-family {
              description "Interface family operations";
            }
            enum bridging-domain {
              description "Bridging domain operations";
            }
            enum routing-instance {
              description "Routing instance operations";
            }
            enum bridge-interface {
              description "Interface bridge operations";
            }
            enum learning-domain {
              description "Learning domain operations";
            }
            enum ipc {
              description "Inter-process communications operations";
            }
            enum mac-learning {
              description "MAC address learning operations";
            }
            enum initialization {
              description "Initialization operations";
            }
            enum flood-next-hop {
              description "Flood next hop operations";
            }
            enum irb {
              description "Integrated routing and bridging operations";
            }
            enum vpls-ping {
              description "VPLS ping operations";
            }
            enum vpls-loop-prev {
              description "VPLS loop prevention";
            }
            enum logical-system {
              description "Logical system operations";
            }
            enum bmac-next-hop {
              description "Backbone Mac Next hop operations ";
            }
            enum bridge-bmac-next-hop {
              description "Bmac Next hop bridge operations";
            }
            enum isid {
              description "I-Tagged Service ID";
            }
            enum mc-ae {
              description "Multi-chassis AE";
            }
            enum kack {
              description "Kernel-acknowledgment";
            }
            enum storm-control {
              description "Storm-control";
            }
            enum redundant-trunk-group {
              description "Redundant trunk group";
            }
            enum unknown-unicast-forwarding {
              description "Trace unknown unicast forwarding events";
            }
            enum vxlan {
              description "VXLAN";
            }
            enum l2-license {
              description "L2 license trace";
            }
            enum telemetry {
              description "Telemetry";
            }
            enum network-isolation {
              description "Network isolation detection";
            }
            enum all {
              description "All operations";
            }
          }
        }
      }
      container kernel {
        description "Trace options for kernel";
        presence "enable kernel";
        container irb {
          description "Trace options for irb";
          presence "enable irb";
        }
      }
      container in-memory-debug {
        description "Enable trace parameters in the memory";
        presence "enable in-memory-debug";
      }
    }
    container global-mac-move {
      description "Enable mac move related options at global level";
      presence "enable global-mac-move";
      leaf notification-time {
        type uint32;
        description "Periodical time interval in secs during which MAC move notification occurs";
        units seconds;
      }
      leaf threshold-time {
        type uint32;
        description "Time during which if certain number of MAC moves happen warrant recording";
        units seconds;
      }
      leaf reopen-time {
        type uint32;
        description "Time after which a blocked interface is reopened";
        units seconds;
      }
      leaf threshold-count {
        type uint32;
        description "Count of MAC moves which warrant recording when happen in certain time";
        units seconds;
      }
      container traceoptions {
        description "Enable logging for the MAC moves";
        leaf no-remote-trace {
          type empty;
          description "Disable remote tracing";
        }
        container file {
          description "Trace file information";
          leaf filename {
            type string {
              length "1 .. 1024";
            }
            description "Name of file in which to write trace information";
          }
          leaf size {
            type string;
            description "Maximum trace file size";
          }
          leaf files {
            type uint32 {
              range "2 .. 1000";
            }
            default "3";
            description "Maximum number of trace files";
          }
          choice world-readable-choice {
            leaf world-readable {
              type empty;
              description "Allow any user to read the log file";
            }
            leaf no-world-readable {
              type empty;
              description "Don't allow any user to read the log file";
            }
          }
          leaf match {
            type "jt:regular-expression";
            description "Regular expression for lines to be logged";
          }
        }
      }
      leaf log {
        type empty;
        description "Syslog all the MAC moves as stored in the mac-move-buffer";
      }
      leaf disable-action {
        type empty;
        description "Disable mac move action globally";
      }
      leaf cooloff-time {
        type uint32;
        description "Time interval in secs during which no further actions are taken";
        units seconds;
      }
      leaf statistical-approach-wait-time {
        type uint32;
        description "Time during which MAC moves are monitored to collect statistics";
        units seconds;
      }
      leaf interface-recovery-time {
        type uint32;
        description "Time interval after which interface is made operationally up";
        units seconds;
      }
      list exclusive-mac {
        description "MAC addresses to be excluded in mac-move-limit or in VPLS loop prevention algorithm";
        key name;
        ordered-by user;
        leaf name {
          type "jt:mac-addr-prefix";
          description "Source MAC address";
        }
      }
    }
    leaf global-mac-table-aging-time {
      type uint32;
      description "System level MAC table aging time";
      units seconds;
    }
    leaf global-mac-ip-table-aging-time {
      type uint32 {
        range "60 .. 1000000";
      }
      description "System level MAC+IP table aging time";
      units seconds;
    }
    leaf global-le-aging-time {
      type uint32 {
        range "120 .. 1000000";
      }
      description "Set LE aging time";
      units seconds;
    }
    leaf global-le-bridge-domain-aging-time {
      type uint32 {
        range "120 .. 1000000";
      }
      description "Set LE bridge-domain aging time";
      units seconds;
    }
    leaf mclag-arpreq-sync {
      type empty;
      description "Enable syncing ARP REQ packets to peer MCLAG PE";
    }
    leaf global-mac-pinning-discard-notification-interval {
      type uint32 {
        range "2 .. 86400";
      }
      description "Set interval for MAC Pinning discard notification";
      units seconds;
    }
    container global-ctx-limit {
      description "Debug context history limit";
      presence "enable global-ctx-limit";
      leaf ctx-limit {
        type uint32 {
          range "0 .. 5000000";
        }
        description "Debug context history limit";
      }
    }
    container global-mac-limit {
      description "System level MAC limit options";
      presence "enable global-mac-limit";
      leaf mac-limit {
        type uint64;
        description "System level MAC limit";
      }
      leaf packet-action {
        type enumeration {
          enum drop {
            description "Enable packet-action drop when MAC limit is reached";
          }
        }
      }
    }
    container global-mac-ip-limit {
      description "System level MAC+IP limit options";
      presence "enable global-mac-ip-limit";
      leaf mac-ip-limit {
        type uint64 {
          range "20 .. 1048575";
        }
        description "System level MAC+IP limit";
      }
    }
    leaf global-mac-statistics {
      type empty;
      description "Enable MAC address statistics at system level";
    }
    leaf global-static-mac-move-drop-log {
      type empty;
      description "Set global static mac move drop and log notification.";
    }
    leaf source-udp-port {
      type uint16 {
        range "49152 .. 65535";
      }
      description "VXLAN source UDP port";
    }
    container telemetry {
      description "Streaming Telemetry Data";
      presence "enable telemetry";
      leaf enable-remote-entries {
        type empty;
        description "Enable Remote mac and mac-ip entries";
      }
    }
    leaf global-no-mac-learning {
      type empty;
      description "Disable dynamic MAC address learning at system level";
    }
    leaf global-no-hw-mac-learning {
      type empty;
      description "Disable hardware MAC-address learning at system level";
    }
    leaf global-no-control-mac-aging {
      type empty;
      description "Disable control MAC-address aging from software";
    }
    leaf mclag-arp-nd-sync {
      type empty;
      description "Arp and ND entry sync from peer device.";
    }
    leaf no-mclag-ifa-sync {
      type empty;
      description "IFA entry disable sync from/to peer device.";
    }
    container platform-parameters {
      description "Platform Parameters Setting";
      presence "enable platform-parameters";
      container no-mac-flush-on-aa-ae-down {
        description "Do not flush MAC & MAC-IP entries when active-active AE interface goes down";
        presence "enable no-mac-flush-on-aa-ae-down";
        choice enable-disable {
          case case_1 {
            leaf disable {
              type empty;
              description "Disable no-mac-flush-on-aa-ae-down";
            }
          }
        }
      }
    }
    container crb-proxy-mac {
      description "Configure proxy MAC address to be used in MAC-IP refresh";
      container family {
        description "Address family";
        container inet {
          description "Inet version 4 family";
          leaf mac-address {
            type "jt:mac-unicast";
            description "Proxy MAC address";
          }
        }
        container inet6 {
          description "Inet version 6 family";
          leaf mac-address {
            type "jt:mac-unicast";
            description "Proxy MAC address";
          }
        }
      }
    }
    leaf arp-nd-probe-disable {
      type empty;
      description "Disable probing for ip address";
    }
    leaf arp-nd-probe-failed-log {
      type empty;
      description "Enable syslog when probing for ip address fails";
    }
    leaf garp-na-enable {
      type empty;
      description "Send GARP or unsolicited NA to all connected access devices";
    }
  }
  grouping juniper-protocols-dot1x {
    container traceoptions {
      description "Trace options for 802.1X";
      container file {
        description "Trace file options";
        leaf filename {
          type string {
            length "1 .. 1024";
          }
          description "Name of file in which to write trace information";
        }
        leaf replace {
          type empty;
          description "Replace trace file rather than appending to it";
          status deprecated;
        }
        leaf size {
          type string;
          description "Maximum trace file size";
        }
        leaf files {
          type uint32 {
            range "2 .. 1000";
          }
          default "10";
          description "Maximum number of trace files";
        }
        leaf no-stamp {
          type empty;
          description "Do not timestamp trace file";
          status deprecated;
        }
        choice world-readable-choice {
          leaf world-readable {
            type empty;
            description "Allow any user to read the log file";
          }
          leaf no-world-readable {
            type empty;
            description "Don't allow any user to read the log file";
          }
        }
      }
      list flag {
        description "Tracing parameters";
        key name;
        ordered-by user;
        leaf name {
          type enumeration {
            enum dot1x-debug {
              description "Trace dot1x events";
            }
            enum parse {
              description "Trace configuration parsing";
            }
            enum esw-if {
              description "Trace ESW Interactions";
            }
            enum eapol {
              description "Trace EAPOL Transmit/Receive";
            }
            enum config-internal {
              description "Trace configuration internals";
            }
            enum normal {
              description "Trace normal events";
            }
            enum general {
              description "Trace general events";
            }
            enum state {
              description "Trace state transitions";
            }
            enum task {
              description "Trace routing protocol task processing";
            }
            enum timer {
              description "Trace routing protocol task timer processing";
            }
            enum vlan {
              description "Trace VLAN transactions";
            }
            enum all {
              description "Trace everything";
            }
            enum dot1x-ipc {
              description "Trace dot1x IPC interactions";
            }
            enum dot1x-event {
              description "Trace dot1x events";
            }
            enum iccp {
              description "Trace iccp events";
            }
          }
        }
        leaf disable {
          type empty;
          description "Disable this trace flag";
        }
      }
    }
    leaf ssl-certificate-path {
      type string;
      default "/var/tmp/";
      description "Load SSL certificates for authentication";
    }
    container authenticator {
      description "802.1X authenticator options";
      presence "enable authenticator";
      leaf authentication-profile-name {
        type string {
          length "1 .. 63";
        }
        description "Access profile name to use for authentication";
      }
      leaf no-mac-table-binding {
        type empty;
        description "Disable association between mac table and dot1x";
      }
      leaf ip-mac-session-binding {
        type empty;
        description "DHCP or DHCPv6 or SLAAC snooping checking for mac ageout";
      }
      leaf dynamic-vlan-cleanup-interval {
        type uint32 {
          range "60 .. 86400";
        }
        description "Dynamic vlan cleanup interval";
        units seconds;
      }
      container radius-reachability {
        description "Enable radius-rechability feature";
        presence "enable radius-reachability";
        leaf query-period {
          type uint32 {
            range "20 .. 65535";
          }
          default "120";
          description "Query period interval";
          units seconds;
        }
      }
      container radius-options {
        description "Info sent to radius server";
        presence "enable radius-options";
        leaf add-interface-text-description {
          type empty;
          description "Appends interface text description to NAS-Port-Id";
        }
        choice vlan {
          case case_1 {
            leaf use-vlan-name {
              type empty;
              description "Vlan name";
            }
          }
          case case_2 {
            leaf use-vlan-id {
              type empty;
              description "Vlan id";
            }
          }
        }
      }
      list static {
        description "Static MAC configuration needed to bypass 802.1X";
        key name;
        ordered-by user;
        leaf name {
          type "jt:mac-addr-prefix";
          description "MAC addresses to bypass authentication";
        }
        leaf vlan-assignment {
          type string;
          description "VLAN name or 802.1q tag for the MAC address";
        }
        leaf bridge-domain-assignment {
          type string;
          description "Bridge-domain name or 802.1q tag for the MAC address";
        }
        leaf interface {
          type "jt:interface-name";
          description "Interface on which authentication is bypassed";
        }
      }
      list interface {
        description "802.1X  interface specific options";
        key name;
        leaf name {
          type string;
        }
        leaf ignore-port-bounce {
          type empty;
          description "To ignore the port-bounce request received from RADIUS server";
        }
        leaf-list authentication-order {
          type enumeration {
            enum dot1x {
              description "Dot1x mode";
            }
            enum mac-radius {
              description "Mac radius mode";
            }
            enum captive-portal {
              description "Captive portal mode";
            }
          }
          description "Flexible authentication order";
          ordered-by user;
        }
        leaf disable {
          type empty;
          description "Disable 802.1X on this interface";
        }
        leaf supplicant {
          type enumeration {
            enum single {
              description "Allow multiple clients; authenticate first client only";
            }
            enum single-secure {
              description "Allow and authenticate only a single client";
            }
            enum multiple {
              description "Allow multiple clients; authenticate each individually";
            }
          }
          default "single";
          description "Set supplicant mode for this interface";
        }
        leaf retries {
          type uint32 {
            range "0 .. 10";
          }
          description "Number of retries after which port is placed into wait state";
        }
        leaf quiet-period {
          type uint32 {
            range "0 .. 65535";
          }
          description "Time to wait after an authentication failure";
          units seconds;
        }
        leaf transmit-period {
          type uint32 {
            range "1 .. 65535";
          }
          description "Interval before retransmitting initial EAPOL PDUs";
          units seconds;
        }
        container multi-domain {
          description "Enable multi domain authentication";
          presence "enable multi-domain";
          leaf packet-action {
            type enumeration {
              enum drop-and-log {
                description " Drop the client and generate the log message";
              }
              enum shutdown {
                description "Disable port for excessive client authentication";
              }
            }
            default "drop-and-log";
            description "Set packet action for this interface";
          }
          leaf max-data-session {
            type uint32 {
              range "1 .. 1000";
            }
            description "Data session limit in multi domain authentication";
          }
          leaf recovery-timeout {
            type uint32 {
              range "60 .. 3600";
            }
            description "Multi domain recovery timeout";
            units seconds;
          }
        }
        container mac-radius {
          description "Enable MAC-RADIUS";
          presence "enable mac-radius";
          leaf restrict {
            type empty;
            description "Bypass dot1x authentication, use MAC RADIUS only";
          }
          leaf flap-on-disconnect {
            type empty;
            description "Reset an interface on receiving a disconnect request";
          }
          container authentication-protocol {
            description "Set mac-radius authentication method";
            choice protocols {
              case case_1 {
                leaf eap-md5 {
                  type empty;
                  description "Authentication protocol EAP-MD5";
                }
              }
              case case_2 {
                leaf pap {
                  type empty;
                  description "Authentication protocol PAP";
                }
              }
              case case_3 {
                container eap-peap {
                  description "Authentication protocol EAP-PEAP";
                  presence "enable eap-peap";
                  leaf resume {
                    type empty;
                    description "Enable resume functionality for faster authentication";
                  }
                }
              }
            }
          }
        }
        choice reauthentication-mode {
          case case_1 {
            leaf no-reauthentication {
              type empty;
              description "Disable reauthentication";
            }
          }
          case case_2 {
            leaf reauthentication {
              type uint32 {
                range "1 .. 65535";
              }
              description "Reauthentication interval";
              units seconds;
            }
          }
        }
        leaf supplicant-timeout {
          type uint32 {
            range "1 .. 60";
          }
          description "Time to wait for a client response";
          units seconds;
        }
        leaf server-timeout {
          type uint32 {
            range "1 .. 60";
          }
          description "Authentication server timeout interval";
          units seconds;
        }
        leaf maximum-requests {
          type uint32 {
            range "1 .. 10";
          }
          description "Number of EAPOL RequestIDs to send before timing out";
        }
        leaf request-retry-count {
          type uint32 {
            range "1 .. 10";
          }
          description "Number of requests to send before timing out";
        }
        leaf guest-vlan {
          type string;
          description "VLAN name or 802.1q tag for unauthenticated or non-responsive hosts";
        }
        leaf guest-gbp-tag {
          type uint32 {
            range "1 .. 65535";
          }
          description "GBP tag for unauthenticated or non-responsive hosts";
        }
        leaf guest-bridge-domain {
          type string;
          description "Bridge-domain name or 802.1q tag for unauthenticated or non-responsive hosts";
        }
        container server-reject-vlan {
          description "VLAN name or 802.1q tag for authentication rejected clients";
          leaf vlan-name {
            type string;
            description "VLAN name or VLAN Tag (1..4095)";
          }
          leaf block-interval {
            type uint32 {
              range "120 .. 65535";
            }
            description "Interval for authenticator to ignore the EAP-Start packets.";
            units seconds;
          }
          leaf eapol-block {
            type empty;
            description "Force the authenticator to ignore EAPOL-Start packets.";
          }
          leaf gbp-tag {
            type uint32 {
              range "1 .. 65535";
            }
            description "GBP tag for authentication rejected clients";
          }
        }
        container server-reject-bridge-domain {
          description "VLAN name or 802.1q tag for authentication rejected clients";
          leaf bridge-domain {
            type string;
            description "Bridge-domain name or VLAN Tag (1..4095)";
          }
          leaf block-interval {
            type uint32 {
              range "120 .. 65535";
            }
            description "Interval for authenticator to ignore the EAP-Start packets.";
            units seconds;
          }
          leaf eapol-block {
            type empty;
            description "Force the authenticator to ignore EAPOL-Start packets.";
          }
        }
        container eapol-block {
          description "Force the authenticator to ignore EAPOL-Start packets";
          container server-fail {
            description "Block EAPOL-Start during RADIUS Timeout";
            presence "enable server-fail";
            leaf block-interval {
              type uint32 {
                range "120 .. 65535";
              }
              description "Interval for authenticator to ignore the EAP-Start packets.";
              units seconds;
            }
          }
          container mac-radius {
            description "Block EAPOL-Start when client is authenticated in mac-radius mode";
            presence "enable mac-radius";
          }
          container captive-portal {
            description "Block EAPOL-Start when client is authenticated in captive-portal mode";
            presence "enable captive-portal";
          }
        }
        leaf lldp-med-bypass {
          type empty;
          description "Bypass dot1x authentication, use lldp-med based authentication";
        }
        container server-fail {
          description "Action to be taken when server is inaccessible";
          leaf gbp-tag {
            type uint32 {
              range "1 .. 65535";
            }
            description "GBP tag to be assigned when server is inaccessible";
          }
          choice server-fail-options {
            case case_1 {
              leaf deny {
                type empty;
                description "Force client authentication to fail";
              }
            }
            case case_2 {
              leaf permit {
                type empty;
                description "Force client authentication to succeed";
              }
            }
            case case_3 {
              leaf vlan-name {
                type string;
                description "VLAN name or 802.1q tag for unreachable servers";
              }
            }
            case case_4 {
              leaf bridge-domain {
                type string;
                description "Bridge-domain name or 802.1q tag for unreachable servers";
              }
            }
            case case_5 {
              leaf use-cache {
                type empty;
                description "Use the previous state of the client";
              }
            }
          }
        }
        container server-fail-voip {
          description "Action to be taken for VOIP client when server is inaccessible";
          choice server-fail-options {
            case case_1 {
              leaf deny {
                type empty;
                description "Force VoIP client authentication to fail";
              }
            }
            case case_2 {
              leaf permit {
                type empty;
                description "Force VoIP client authentication to succeed";
              }
            }
            case case_3 {
              leaf vlan-name {
                type string;
                description "Configured VoIP VLAN name or 802.1q tag for unreachable servers";
              }
            }
            case case_4 {
              leaf use-cache {
                type empty;
                description "Use the previous state of the VoIP client";
              }
            }
          }
        }
        leaf redirect-url {
          type string {
            length "10 .. 247";
          }
          description "CWA redirect URL to be used for unauthenticated users";
        }
        leaf no-tagged-mac-authentication {
          type empty;
          description "Don't allow tagged mac for radius authentication";
        }
        leaf retain-mac-aged-session {
          type empty;
          description "Retain mac aged out session";
        }
      }
      container mac-radius {
        description "User-defined options for mac-radius mode";
        presence "enable mac-radius";
        leaf password {
          type string {
            length "1 .. 128";
          }
          description "Specify the user-defined password to be used for mac authentication";
        }
      }
    }
    container supplicant {
      description "802.1X supplicant options";
      list interface {
        description "802.1X supplicant interface specific options";
        key name;
        leaf name {
          type string;
        }
        leaf authentication-method {
          type enumeration {
            enum eap-tls {
              description "Supplicant authentication protocol EAP-TLS";
            }
          }
          default "eap-tls";
          description "802.1X supplicant authentication protocol for this interface";
        }
        leaf local-certificate {
          type string;
          description "Local certificate identifier to be presented for authentication";
        }
        leaf user-id {
          type string {
            length "1 .. 63";
          }
          description "User id, to be presented for authentication";
        }
        leaf password {
          type string {
            length "1 .. 63";
          }
          description "Password, to be presented for authentication";
        }
      }
    }
  }
  grouping juniper-protocols-esis {
    choice enable-disable {
      case case_1 {
        leaf disable {
          type empty;
          description "Disable ES-IS";
        }
      }
    }
    container traceoptions {
      description "Trace options for ES-IS";
      container file {
        description "Trace file options";
        leaf filename {
          type string {
            length "1 .. 1024";
          }
          description "Name of file in which to write trace information";
        }
        leaf replace {
          type empty;
          description "Replace trace file rather than appending to it";
          status deprecated;
        }
        leaf size {
          type string;
          description "Maximum trace file size";
        }
        leaf files {
          type uint32 {
            range "2 .. 1000";
          }
          default "10";
          description "Maximum number of trace files";
        }
        leaf no-stamp {
          type empty;
          description "Do not timestamp trace file";
          status deprecated;
        }
        choice world-readable-choice {
          leaf world-readable {
            type empty;
            description "Allow any user to read the log file";
          }
          leaf no-world-readable {
            type empty;
            description "Don't allow any user to read the log file";
          }
        }
      }
      list flag {
        description "Tracing parameters";
        key name;
        ordered-by user;
        leaf name {
          type enumeration {
            enum error {
              description "Trace errored packets";
            }
            enum esh {
              description "Trace end system hello packets";
            }
            enum ish {
              description "Trace intermediate system hello packets";
            }
            enum graceful-restart {
              description "Trace graceful restart events";
            }
            enum route {
              description "Trace routing information";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
        leaf send {
          type empty;
          description "Trace transmitted packets";
        }
        leaf receive {
          type empty;
          description "Trace received packets";
        }
        leaf detail {
          type empty;
          description "Trace detailed information";
        }
        leaf disable {
          type empty;
          description "Disable this trace flag";
        }
      }
    }
    leaf preference {
      type uint32;
      description "Preference of routes";
    }
    container graceful-restart {
      description "ES-IS graceful restart options";
      choice enable-disable {
        case case_1 {
          leaf disable {
            type empty;
            description "Disable graceful restart";
          }
        }
      }
      leaf restart-duration {
        type uint32 {
          range "30 .. 300";
        }
        description "Maximum time for graceful restart to finish";
        units seconds;
      }
    }
    list interface {
      description "Interface configuration";
      key name;
      leaf name {
        type "jt:interface-name";
        description "Interface name";
      }
      leaf hold-time {
        type uint32 {
          range "1 .. 65535";
        }
        description "Time after which neighbors think the interface is down";
        units seconds;
      }
      leaf end-system-configuration-timer {
        type uint32 {
          range "1 .. 65535";
        }
        description "Suggested end system configuration timer";
        units seconds;
      }
      choice enable-disable {
        case case_1 {
          leaf disable {
            type empty;
            description "Disable ES-IS on this interface";
          }
        }
      }
    }
  }
  grouping juniper-protocols-evpn-interconnect {
    description "Interconnect configuration for the routing instance";
    leaf-list vrf-import {
      type "jt:policy-algebra";
      description "Import policy for Interconnect";
      ordered-by user;
    }
    leaf-list vrf-export {
      type "jt:policy-algebra";
      description "Export policy for Interconnect";
      ordered-by user;
    }
    container vrf-target {
      description "Interconnect target community configuration";
      leaf community {
        type string;
        description "Target community to use in import and export";
      }
      leaf import {
        type string;
        description "Target community to use when filtering on import";
      }
      leaf export {
        type string;
        description "Target community to use when marking routes on export";
      }
    }
    container route-distinguisher {
      description "Route distinguisher for this interconnect";
      leaf rd-type {
        type string;
        description "Number in (16 bit:32 bit) or (32 bit 'L':16 bit) or (IP address:16 bit) format";
      }
    }
    list domain-path-id {
      description "DCI VRF domain path id configuration";
      key name;
      max-elements 1;
      ordered-by user;
      uses domain-id-type;
    }
    container esi {
      description "ESI configuration of interconnect";
      leaf identifier {
        type "jt:esi";
        description "ESI value for interconnect";
      }
      choice mode {
        case case_1 {
          leaf all-active {
            type empty;
            description "All-active mode";
          }
        }
      }
      container df-election-type {
        description "DF Election Type";
        presence "enable df-election-type";
        choice pref_choice {
          case case_1 {
            container preference {
              description "Preference based DF election";
              presence "enable preference";
              leaf value {
                type uint32 {
                  range "0 .. 65535";
                }
                default "32767";
                description "Preference value for EVPN Multihoming DF election";
              }
            }
          }
        }
        choice mod_choice {
          case case_1 {
            container mod {
              description "MOD based DF election";
              presence "enable mod";
            }
          }
        }
      }
    }
    leaf-list interconnected-vni-list {
      type string;
      description "List of translated VNIs (1..16777214) or all, that are to be EVPN interconnected";
    }
    leaf-list interconnected-vlan-list {
      type string;
      description "List of VLAN identifiers that are to be EVPN interconnected";
      ordered-by user;
    }
    container irb-symmetric-routing {
      description "Enable EVPN T-2 symmetric DCI routing";
      leaf vni {
        type uint32 {
          range "1 .. 16777214";
        }
        description "VXLAN network identifier used for T-2 symmetric routing IP prefixes";
      }
    }
    leaf encapsulation {
      type enumeration {
        enum mpls {
          description "MPLS encapsulation";
        }
        enum vxlan {
          description "VXLAN encapsulation";
        }
      }
    }
  }
  grouping domain-id-type {
    leaf name {
      type string;
      description "Domain id for type 5 evpn DCI";
    }
  }
  grouping juniper-protocols-isis {
    list interface {
      description "Interface configuration";
      key name;
      leaf name {
        type "jt:interface-name";
        description "Interface name";
      }
      container ldp-synchronization {
        description "Advertise maximum metric until LDP is operational";
        presence "enable ldp-synchronization";
        uses ldp-sync-obj;
      }
      list level {
        description "Configure levels on this interface";
        key name;
        ordered-by user;
        leaf name {
          type uint32 {
            range "1 .. 2";
          }
          description "IS-IS level number";
        }
        choice enable-disable {
          case case_1 {
            leaf disable {
              type empty;
              description "Disable IS-IS for this level";
            }
          }
        }
        leaf metric {
          type uint32 {
            range "0 .. 16777215";
          }
          description "Metric for this level";
        }
      }
      leaf lsp-interval {
        type uint32 {
          range "1 .. 1000";
        }
        default "100";
        description "Interval between LSP transmissions";
        units milliseconds;
      }
      leaf point-to-point {
        type empty;
        description "Treat interface as point to point";
      }
      container passive {
        description "Do not run IS-IS, but advertise it";
        presence "enable passive";
        leaf remote-node-iso {
          type "jt:sysid";
          description "ISO System-ID of the remote node";
        }
        leaf remote-node-id {
          type "jt:ipv4addr";
          description "Remote address of the link";
        }
      }
      list family {
        description "Address family specific interface attributes";
        key name;
        ordered-by user;
        leaf name {
          type enumeration {
            enum inet {
              description "IPv4 family";
            }
            enum inet6 {
              description "IPv6 family";
            }
          }
        }
        container bfd-liveness-detection {
          description "Bidirectional Forwarding Detection options";
          leaf version {
            type enumeration {
              enum 0 {
                description "BFD version 0 (deprecated)";
              }
              enum 1 {
                description "BFD version 1";
              }
              enum automatic {
                description "Choose BFD version automatically";
              }
            }
            default "automatic";
            description "BFD protocol version number";
          }
          leaf minimum-interval {
            type uint32 {
              range "1 .. 255000";
            }
            description "Minimum transmit and receive interval";
            units milliseconds;
          }
          leaf minimum-transmit-interval {
            type uint32 {
              range "1 .. 255000";
            }
            description "Minimum transmit interval";
            status deprecated;
            units milliseconds;
          }
          leaf minimum-receive-interval {
            type uint32 {
              range "1 .. 255000";
            }
            description "Minimum receive interval";
            units milliseconds;
          }
          leaf multiplier {
            type uint32 {
              range "1 .. 255";
            }
            default "3";
            description "Detection time multiplier";
          }
          leaf inline-disable {
            type empty;
            description "Disable inline mode for this BFD session";
          }
          leaf pdu-size {
            type uint32 {
              range "24 .. 9000";
            }
            default "24";
            description "BFD transport protocol payload size";
          }
          choice adaptation-choice {
            case case_1 {
              leaf no-adaptation {
                type empty;
                description "Disable adaptation";
              }
            }
          }
          container transmit-interval {
            description "Transmit-interval options";
            leaf minimum-interval {
              type uint32 {
                range "1 .. 255000";
              }
              description "Minimum transmit interval";
              units milliseconds;
            }
            leaf threshold {
              type uint32;
              description "High transmit interval triggering a trap";
              units milliseconds;
            }
          }
          container detection-time {
            description "Detection-time options";
            leaf threshold {
              type uint32;
              description "High detection-time triggering a trap";
              units milliseconds;
            }
          }
          container authentication {
            description "Authentication options";
            leaf key-chain {
              type string;
              description "Key chain name";
            }
            leaf algorithm {
              type enumeration {
                enum simple-password {
                  description "Simple password";
                }
                enum keyed-md5 {
                  description "Keyed message Digest 5";
                }
                enum meticulous-keyed-md5 {
                  description "Meticulous keyed message Digest 5";
                }
                enum keyed-sha-1 {
                  description "Keyed secure hash algorithm (SHA1) ";
                }
                enum meticulous-keyed-sha-1 {
                  description "Meticulous keyed secure hash algorithm (SHA1) ";
                }
              }
              description "Algorithm name";
            }
            leaf loose-check {
              type empty;
              description "Verify authentication only if authentication is negotiated";
            }
          }
          container echo {
            description "Echo mode parameters";
            leaf minimum-interval {
              type uint32 {
                range "100 .. 255000";
              }
              description "Minimum transmit and receive interval";
              units milliseconds;
            }
          }
          container echo-lite {
            description "Echo-lite more parameters";
            leaf minimum-interval {
              type uint32 {
                range "100 .. 255000";
              }
              description "Minimum transmit and receive interval";
              units milliseconds;
            }
          }
          leaf holddown-interval {
            type uint32 {
              range "0 .. 255000";
            }
            description "Time to hold the session-UP notification to the client";
            units milliseconds;
          }
        }
      }
    }
    container source-packet-routing {
      description "Enable Source Packet Routing (SPRING)";
      presence "enable source-packet-routing";
      container adjacency-segment {
        description "Configure attributes for Adjacency Segments in SPRING";
        leaf hold-time {
          type uint32 {
            range "180000 .. 900000";
          }
          description "Duration(ms) for which adjacency segments will be retained after isolating from an interface";
        }
      }
      container udp-tunneling {
        description "Enable SR over UDP feature";
        leaf encapsulation {
          type empty;
          description "Enable UDP Tunnel Encapsulation";
        }
        leaf decapsulation {
          type empty;
          description "Enable UDP Tunnel decapsulation";
        }
      }
      container srgb {
        description "Set the SRGB global block in SPRING";
        leaf start-label {
          type uint32;
          description "Start range for SRGB label block";
        }
        leaf index-range {
          type uint32;
          description "Index to the SRGB start label block";
        }
      }
      container node-segment {
        description "Enable support for Node segments in SPRING";
        leaf ipv4-index {
          type uint32 {
            range "0 .. 199999";
          }
          description "Set IPv4 Node Segment index";
        }
        leaf ipv6-index {
          type uint32 {
            range "0 .. 199999";
          }
          description "Set IPv6 Node Segment index";
        }
        leaf index-range {
          type uint32 {
            range "32 .. 16385";
          }
          description "Set Range of Node Segment indices allowed";
        }
      }
      leaf-list flex-algorithm {
        type uint32 {
          range "128 .. 255";
        }
        description "Flex-algorithms we would like to participate in";
        max-elements 16;
      }
      leaf use-flex-algorithm-metric-always {
        type empty;
        description "Use flex-algo prefix metric whenever available";
      }
      leaf strict-asla-based-flex-algorithm {
        type empty;
        description "Flex-Algorithm to ignore links not having ASLA sub-TLVs";
      }
      leaf new-capability-subtlv {
        type empty;
        description "Advertise all ranges in single spring capability subtlv";
      }
      leaf explicit-null {
        type empty;
        description "Set E and P bits in all Prefix SID advertisements";
      }
      leaf mapping-server {
        type string;
        description "Mapping server name";
      }
      leaf no-strict-spf {
        type empty;
        description " Disable strict spf algo 1 advertisement";
      }
      leaf no-binding-sid-leaking {
        type empty;
        description " Disable SRMS binding sid leaking";
      }
      leaf ldp-stitching {
        type empty;
        description "Enable SR to LDP stitching";
      }
      container srv6 {
        description "Enable IPv6 Segment Routing (SRv6)";
        presence "enable srv6";
        list locator {
          description "SRv6 Locator";
          key name;
          ordered-by user;
          leaf name {
            type string;
            description "Locator name";
          }
          leaf anycast {
            type empty;
            description "Set A flag in the Prefix-Attribute sub-TLV";
          }
          list end-sid {
            key name;
            ordered-by user;
            leaf name {
              type "jt:ipv6addr";
            }
            container flavor {
              description "Configure end-SID flavor";
              presence "enable flavor";
              leaf psp {
                type empty;
                description "Penultimate segment pop of the SRH";
              }
              leaf usp {
                type empty;
                description "Ultimate segment pop of the SRH";
              }
              leaf usd {
                type empty;
                description "Ultimate segment decapsulation";
              }
            }
          }
          container dynamic-end-sid {
            description "Allocate end SID dynamically";
            presence "enable dynamic-end-sid";
            container flavor {
              description "Configure end-SID flavor";
              presence "enable flavor";
              leaf psp {
                type empty;
                description "Penultimate segment pop of the SRH";
              }
              leaf usp {
                type empty;
                description "Ultimate segment pop of the SRH";
              }
              leaf usd {
                type empty;
                description "Ultimate segment decapsulation";
              }
            }
          }
          leaf micro-node-sid {
            type empty;
            description "Program and advertise micro-node-SID";
          }
        }
      }
      container sensor-based-stats {
        description "Configure sensor based stats in SPRING";
        container per-interface-per-member-link {
          description "Configure sensor based stats per nexthop";
          leaf ingress {
            type empty;
            description "Enable sensor based stats on ingress interface";
          }
          leaf egress {
            type empty;
            description "Enable sensor based stats on egress interface";
          }
        }
        container per-sid {
          description "Configure sensor based stats per spring route";
          leaf ingress {
            type empty;
            description "Enable sensor based stats for per-sid ingress accounting";
          }
          leaf egress {
            type empty;
            description "Enable sensor based stats for IP-MPLS egress accounting";
          }
        }
        container subscribe {
          description "Enable on-box sensor-based statistics collection";
          presence "enable subscribe";
          leaf interval {
            type uint32 {
              range "30 .. 86400";
            }
            description "Statistics collection interval (seconds)";
          }
        }
      }
      container traffic-statistics {
        description "Enable support for traffic statistics in SPRING";
        container statistics-granularity {
          description "Granularity for traffic statistics in SPRING";
          leaf per-interface {
            type empty;
            description "Interface Based traffic statistics in SPRING";
          }
        }
        leaf congestion-protection {
          type empty;
          description "Enable tactical traffic engineering";
        }
        leaf auto-bandwidth {
          type string;
          description "Auto bandwidth name";
        }
      }
    }
    list level {
      description "Configure global level attributes";
      key name;
      ordered-by user;
      leaf name {
        type uint32 {
          range "1 .. 2";
        }
        description "IS-IS level number";
      }
      choice enable-disable {
        case case_1 {
          leaf disable {
            type empty;
            description "Disable IS-IS on this level";
          }
        }
      }
      leaf authentication-key {
        type "jt:unreadable";
        description "Authentication key (password)";
      }
      leaf authentication-type {
        type enumeration {
          enum md5 {
            description "MD5 authentication";
          }
          enum simple {
            description "Simple password authentication";
          }
        }
        description "Authentication type";
      }
      leaf no-hello-authentication {
        type empty;
        description "Disable authentication for hello packets";
      }
      leaf no-csnp-authentication {
        type empty;
        description "Disable authentication for CSN packets";
      }
      leaf no-psnp-authentication {
        type empty;
        description "Disable authentication for PSN packets";
      }
      leaf wide-metrics-only {
        type empty;
        description "Generate wide metrics only";
      }
    }
    leaf lsp-lifetime {
      type uint32 {
        range "350 .. 65535";
      }
      description "Lifetime of LSPs";
      units seconds;
    }
  }
  grouping juniper-protocols-l2control {
    container traceoptions {
      description "Global tracing options for STP";
      container file {
        description "Trace file options";
        leaf filename {
          type string {
            length "1 .. 1024";
          }
          description "Name of file in which to write trace information";
        }
        leaf replace {
          type empty;
          description "Replace trace file rather than appending to it";
          status deprecated;
        }
        leaf size {
          type string;
          description "Maximum trace file size";
        }
        leaf files {
          type uint32 {
            range "2 .. 1000";
          }
          default "10";
          description "Maximum number of trace files";
        }
        leaf no-stamp {
          type empty;
          description "Do not timestamp trace file";
          status deprecated;
        }
        choice world-readable-choice {
          leaf world-readable {
            type empty;
            description "Allow any user to read the log file";
          }
          leaf no-world-readable {
            type empty;
            description "Don't allow any user to read the log file";
          }
        }
      }
      list flag {
        description "Tracing parameters";
        key name;
        ordered-by user;
        leaf name {
          type enumeration {
            enum parse {
              description "Trace configuration parsing";
            }
            enum regex-parse {
              description "Trace regular-expression parsing";
            }
            enum config-internal {
              description "Trace configuration internals";
            }
            enum normal {
              description "Trace normal events";
            }
            enum general {
              description "Trace general events";
            }
            enum state {
              description "Trace state transitions";
            }
            enum task {
              description "Trace routing protocol task processing";
            }
            enum timer {
              description "Trace routing protocol task timer processing";
            }
            enum ppmlite {
              description "Trace libppmlite processing";
            }
            enum all {
              description "Trace everything";
            }
          }
        }
        leaf disable {
          type empty;
          description "Disable this trace flag";
        }
      }
    }
    leaf nonstop-bridging {
      type empty;
      description "Enable nonstop operation";
    }
    container options {
      description "Layer2 control options";
      container nsb-extended-timers {
        description "Extend expiration of timers during switchover";
        presence "enable nsb-extended-timers";
        choice enable-disable {
          case case_1 {
            leaf disable {
              type empty;
              description "Disable timer extension during switchover";
            }
          }
        }
      }
      container nsb-optimized-config-read {
        description "Optimize config re-prasing during switchover";
        presence "enable nsb-optimized-config-read";
        choice enable-disable {
          case case_1 {
            leaf disable {
              type empty;
              description "Disable optimized re-parsing of config during switchover";
            }
          }
        }
      }
    }
    choice ephemeral-db-support-choice {
      leaf ephemeral-db-support {
        type empty;
        description "Enable ephemeral DB supoort for STP";
      }
      leaf no-ephemeral-db-support {
        type empty;
        description "Don't enable ephemeral DB supoort for STP";
      }
    }
    container bpdu-block {
      description "Block BPDU on interface (BPDU Protect)";
      presence "enable bpdu-block";
      list interface {
        description "Interface name to block BPDU on";
        key name;
        ordered-by user;
        leaf name {
          type string;
        }
        leaf disable {
          type empty;
          description "Disable bpdu-block on a port";
        }
        leaf drop {
          type empty;
          description "Drop xSTP BPDUs";
        }
      }
      leaf disable-timeout {
        type int32 {
          range "10 .. 3600";
        }
        description "Disable timeout for BPDU Protect";
        units seconds;
      }
    }
    container l2pt {
      description "L2 protocol tunneling functionality";
      list interface {
        key name;
        ordered-by user;
        leaf name {
          type "jt:interface-device";
        }
        leaf enable-all-ifl {
          type empty;
          description "Enable tunneling for all the IFLs under the interface";
        }
        container protocol {
          description "Protocols for which L2 protocol tunneling need to be enabled";
          container stp {
            description "Enable L2 protocol tunneling for STP";
            presence "enable stp";
          }
          container vtp {
            description "Enable L2 protocol tunneling for VTP";
            presence "enable vtp";
          }
          container cdp {
            description "Enable L2 protocol tunneling for CDP";
            presence "enable cdp";
          }
          container ieee8021x {
            description "Enable L2 protocol tunneling for 8021X";
            presence "enable ieee8021x";
          }
          container ieee8023ah {
            description "Enable L2 protocol tunneling for 8023AH";
            presence "enable ieee8023ah";
          }
          container elmi {
            description "Enable L2 protocol tunneling for ELMI";
            presence "enable elmi";
          }
          container lacp {
            description "Enable L2 protocol tunneling for LACP";
            presence "enable lacp";
          }
          container lldp {
            description "Enable L2 protocol tunneling for LLDP";
            presence "enable lldp";
          }
          container mmrp {
            description "Enable L2 protocol tunneling for MMRP";
            presence "enable mmrp";
          }
          container mvrp {
            description "Enable L2 protocol tunneling for MVRP";
            presence "enable mvrp";
          }
          container pvstp {
            description "Enable L2 protocol tunneling for PVSTP+";
            presence "enable pvstp";
          }
          container gvrp {
            description "Enable L2 protocol tunneling for GVRP";
            presence "enable gvrp";
          }
          container vstp {
            description "Enable L2 protocol tunneling for VSTP";
            presence "enable vstp";
          }
          container udld {
            description "Enable L2 protocol tunneling for UDLD";
            presence "enable udld";
          }
          container all {
            description "Enable L2 protocol tunneling for all protocols";
            presence "enable all";
          }
        }
        container destination {
          description "Destination tunnel for which L2 protocol tunneling need to be enabled";
          leaf vxlan-tunnel {
            type empty;
            description "Enable L2 protocol tunneling in vxlan-tunnel";
          }
        }
      }
    }
    container mac-rewrite {
      description "Mac rewrite functionality";
      list interface {
        key name;
        ordered-by user;
        leaf name {
          type "jt:interface-device";
        }
        leaf enable-all-ifl {
          type empty;
          description "Enable tunneling for all the IFLs under the interface";
        }
        container protocol {
          description "Protocols for which L2 protocol tunneling need to be enabled";
          container stp {
            description "Enable L2 protocol tunneling for STP";
            presence "enable stp";
          }
          container vtp {
            description "Enable L2 protocol tunneling for VTP";
            presence "enable vtp";
          }
          container cdp {
            description "Enable L2 protocol tunneling for CDP";
            presence "enable cdp";
          }
          container ieee8021x {
            description "Enable L2 protocol tunneling for 8021X";
            presence "enable ieee8021x";
          }
          container ieee8023ah {
            description "Enable L2 protocol tunneling for 8023AH";
            presence "enable ieee8023ah";
          }
          container elmi {
            description "Enable L2 protocol tunneling for ELMI";
            presence "enable elmi";
          }
          container lacp {
            description "Enable L2 protocol tunneling for LACP";
            presence "enable lacp";
          }
          container lldp {
            description "Enable L2 protocol tunneling for LLDP";
            presence "enable lldp";
          }
          container mmrp {
            description "Enable L2 protocol tunneling for MMRP";
            presence "enable mmrp";
          }
          container mvrp {
            description "Enable L2 protocol tunneling for MVRP";
            presence "enable mvrp";
          }
          container pvstp {
            description "Enable L2 protocol tunneling for PVSTP+";
            presence "enable pvstp";
          }
          container gvrp {
            description "Enable L2 protocol tunneling for GVRP";
            presence "enable gvrp";
          }
          container vstp {
            description "Enable L2 protocol tunneling for VSTP";
            presence "enable vstp";
          }
          container udld {
            description "Enable L2 protocol tunneling for UDLD";
            presence "enable udld";
          }
          container all {
            description "Enable L2 protocol tunneling for all protocols";
            presence "enable all";
          }
        }
      }
      container tunnel-destination-mac {
        description "Tunnel destination mac to be used in L2PT packets";
        presence "enable tunnel-destination-mac";
        leaf source {
          type "jt:mac-multicast";
          description "L2 multicast mac to be used as tunnel destination mac";
        }
      }
    }
  }
  grouping juniper-protocols-ldp {
    container traffic-statistics {
      description "Collect statistics for LDP label-switched paths";
      container file {
        description "Statistics file options";
        leaf filename {
          type string {
            length "1 .. 1024";
          }
          description "Name of file in which to write trace information";
        }
        leaf replace {
          type empty;
          description "Replace trace file rather than appending to it";
          status deprecated;
        }
        leaf size {
          type string;
          description "Maximum trace file size";
        }
        leaf files {
          type uint32 {
            range "2 .. 1000";
          }
          default "10";
          description "Maximum number of trace files";
        }
        leaf no-stamp {
          type empty;
          description "Do not timestamp trace file";
          status deprecated;
        }
        choice world-readable-choice {
          leaf world-readable {
            type empty;
            description "Allow any user to read the log file";
          }
          leaf no-world-readable {
            type empty;
            description "Don't allow any user to read the log file";
          }
        }
      }
      leaf interval {
        type int32 {
          range "60 .. 65535";
        }
        description "Time to collect statistics (seconds)";
      }
      leaf sensor-based-stats {
        type empty;
        description "Enable sensor based statistics collection";
      }
      leaf no-penultimate-hop {
        type empty;
        description "No penultimate hop statistics collection";
      }
    }
    leaf preference {
      type uint32;
      description "Route preference";
    }
    container transport-address {
      description "Address used for TCP sessions";
      choice address-choice {
        case case_1 {
          leaf router-id {
            type empty;
            description "Use router ID for TCP connections";
          }
        }
        case case_2 {
          leaf interface {
            type empty;
            description "Use interface address for TCP connections";
          }
        }
        case case_3 {
          leaf address {
            type "jt:ipaddr";
            description "Use specified address for TCP connections";
          }
        }
      }
    }
    list interface {
      description "Enable LDP on this interface";
      key name;
      leaf name {
        type "jt:interface-name";
        description "Interface name";
      }
      choice enable-disable {
        case case_1 {
          leaf disable {
            type empty;
            description "Disable LDP on this interface";
          }
        }
      }
      leaf hello-interval {
        type uint32 {
          range "1 .. 65535";
        }
        description "Hello interval (seconds)";
      }
      leaf hold-time {
        type uint32 {
          range "1 .. 65535";
        }
        description "Hello hold time (seconds)";
      }
      container link-protection {
        description "Enable link protection to protect interface for link faults only";
        presence "enable link-protection";
        choice enable-disable {
          case case_1 {
            leaf disable {
              type empty;
              description "Disable link-protection";
            }
          }
        }
        leaf dynamic-rsvp-lsp {
          type empty;
          description "Enable setup of dynamic rsvp lsp for link protection";
        }
      }
      container transport-address {
        description "Address used for TCP sessions";
        choice address-choice {
          case case_1 {
            leaf router-id {
              type empty;
              description "Use router ID for TCP connections";
            }
          }
          case case_2 {
            leaf interface {
              type empty;
              description "Use interface address for TCP connections";
            }
          }
          case case_3 {
            leaf address {
              type "jt:ipaddr";
              description "Use specified address for TCP connections";
            }
          }
        }
      }
      choice allow-subnet-mismatch-choice {
        leaf allow-subnet-mismatch {
          type empty;
          description "Allow subnet mismatch for source address in hello packet";
        }
        leaf no-allow-subnet-mismatch {
          type empty;
          description "Don't allow subnet mismatch for source address in hello packet";
        }
      }
    }
  }
  grouping juniper-protocols-lmp {
    list te-link {
      description "Traffic engineering link";
      key name;
      ordered-by user;
      leaf name {
        type string;
        description "Name of TE link";
      }
      leaf local-address {
        type "jt:ipaddr";
        description "Address of the local end of the link";
      }
      leaf remote-address {
        type "jt:ipaddr";
        description "Address of the remote end of the link";
      }
      leaf remote-id {
        type uint32 {
          range "1 .. 4294967295";
        }
        description "Link ID for the remote end of the link";
      }
      leaf te-metric {
        type uint32 {
          range "1 .. 65535";
        }
        description "Traffic engineering metric of the link";
      }
      choice enable-disable {
        case case_1 {
          leaf disable {
            type empty;
            description "Disable TE link";
          }
        }
      }
      container ethernet-vlan {
        description "TE link used for setup of  L2 VLAN LSP";
        presence "enable ethernet-vlan";
        leaf-list vlan-id-range {
          type "jt:vlan-range";
          description "VLAN id";
          max-elements 1;
        }
      }
      choice resource-option {
        case case_1 {
          list interface {
            description "Member interface of TE link";
            key name;
            ordered-by user;
            leaf name {
              type "jt:interface-device";
              description "Interface name";
            }
            leaf local-address {
              type "jt:ipaddr";
              description "Local address of the resource";
            }
            leaf remote-address {
              type "jt:ipaddr";
              description "Remote address of the resource";
            }
            leaf remote-id {
              type uint32 {
                range "1 .. 4294967295";
              }
              description "Interface ID for the remote end of the resource";
            }
            choice enable-disable {
              case case_1 {
                leaf disable {
                  type empty;
                  description "Disable resource on this TE link";
                }
              }
            }
          }
        }
        case case_2 {
          list label-switched-path {
            description "Member forwarding adjacency LSP of TE link";
            key name;
            max-elements 1;
            ordered-by user;
            leaf name {
              type string;
              description "Name of label-switched path";
            }
            leaf local-address {
              type "jt:ipaddr";
              description "Local address of the resource";
            }
            leaf remote-address {
              type "jt:ipaddr";
              description "Remote address of the resource";
            }
            leaf remote-id {
              type uint32 {
                range "1 .. 4294967295";
              }
              description "Interface ID for the remote end of the resource";
            }
            choice enable-disable {
              case case_1 {
                leaf disable {
                  type empty;
                  description "Disable resource on this TE link";
                }
              }
            }
          }
        }
      }
    }
    list peer {
      description "Define a network or LMP peer";
      key name;
      ordered-by user;
      leaf name {
        type string;
        description "Name of peer";
      }
      leaf address {
        type "jt:ipaddr";
        description "Address of peer";
      }
      container lmp-protocol {
        description "LMP protocol attributes";
        presence "enable lmp-protocol";
        leaf hello-interval {
          type uint32 {
            range "150 .. 21845";
          }
          description "Interval between Hello messages";
          units milliseconds;
        }
        leaf hello-dead-interval {
          type uint32 {
            range "500 .. 65535";
          }
          description "Delay for control channel shutdown when no Hello received";
          units milliseconds;
        }
        leaf retransmission-interval {
          type uint32 {
            range "500 .. 300000";
          }
          description "Minimum time before retransmitting a message";
          units milliseconds;
        }
        leaf retry-limit {
          type uint32 {
            range "3 .. 1000";
          }
          description "Number of times to retransmit a message";
        }
        leaf passive {
          type empty;
          description "Do not send Config messages to peer";
        }
      }
      leaf-list control-channel {
        type "jt:interface-name";
        description "Control channel interfaces by priority";
        ordered-by user;
      }
      list lmp-control-channel {
        description "Control channel IDs";
        key name;
        ordered-by user;
        uses lmp_control_channel_type;
      }
      leaf-list te-link {
        type string;
        description "List of TE links managed by this peer";
        ordered-by user;
      }
    }
    container traceoptions {
      description "LMP trace options";
      container file {
        description "Trace file options";
        leaf filename {
          type string {
            length "1 .. 1024";
          }
          description "Name of file in which to write trace information";
        }
        leaf replace {
          type empty;
          description "Replace trace file rather than appending to it";
          status deprecated;
        }
        leaf size {
          type string;
          description "Maximum trace file size";
        }
        leaf files {
          type uint32 {
            range "2 .. 1000";
          }
          default "10";
          description "Maximum number of trace files";
        }
        leaf no-stamp {
          type empty;
          description "Do not timestamp trace file";
          status deprecated;
        }
        choice world-readable-choice {
          leaf world-readable {
            type empty;
            description "Allow any user to read the log file";
          }
          leaf no-world-readable {
            type empty;
            description "Don't allow any user to read the log file";
          }
        }
      }
      list flag {
        description "Tracing parameters";
        key name;
        ordered-by user;
        leaf name {
          type enumeration {
            enum init {
              description "Trace initialization events";
            }
            enum show {
              description "Trace show command servicing";
            }
            enum route-socket {
              description "Trace route-socket events";
            }
            enum parse {
              description "Trace parser processing";
            }
            enum process {
              description "Trace general configuration processing";
            }
            enum server {
              description "Trace server processing";
            }
            enum routing {
              description "Trace routing protocols interworking";
            }
            enum packets {
              description "Trace packet processing";
            }
            enum hello-packets {
              description "Trace hello packet processing";
            }
            enum state {
              description "Trace state transitions";
            }
            enum nsr-synchronization {
              description "Trace mirror and nsr transitions";
            }
            enum all {
              description "Trace everything";
            }
          }
        }
        leaf send {
          type empty;
          description "Trace transmitted packets";
          status deprecated;
        }
        leaf receive {
          type empty;
          description "Trace received packets";
          status deprecated;
        }
        leaf detail {
          type empty;
          description "Trace detailed information";
          status deprecated;
        }
        leaf disable {
          type empty;
          description "Disable this trace flag";
          status deprecated;
        }
      }
    }
  }
  grouping juniper-protocols-mpls {
    description "Multiprotocol Label Switching options";
    leaf no-propagate-ttl {
      type empty;
      description "Disable TTL propagation from IP to MPLS (on push) and MPLS to IP (on pop)";
    }
    leaf ipv6-tunneling {
      type empty;
      description "Allow MPLS LSPs to be used for tunneling IPv6 traffic";
    }
    list interface {
      description "MPLS interface options";
      key name;
      ordered-by user;
      uses juniper-protocols-mpls-interface;
    }
  }
  grouping juniper-protocols-mpls-interface {
    leaf name {
      type "jt:interface-name";
      description "Interface name";
    }
    choice enable-disable {
      case case_1 {
        leaf disable {
          type empty;
          description "Disable MPLS on this interface";
        }
      }
    }
    leaf-list srlg {
      type string;
      description "SRLG Name";
      max-elements 64;
      ordered-by user;
    }
    leaf always-mark-connection-protection-tlv {
      type empty;
      description "Mark connection protection tlv on this interface";
    }
    leaf switch-away-lsps {
      type empty;
      description "Switch away protected LSPs to their bypass LSPs";
    }
    leaf-list admin-group {
      type string;
      description "Administrative groups";
      ordered-by user;
    }
    leaf-list admin-group-extended {
      type string;
      description "Extended administrative groups";
      ordered-by user;
    }
    container static {
      description "Static label-switch path related configurations";
      leaf protection-revert-time {
        type uint32 {
          range "0 .. 65535";
        }
        description "FRR revert wait time, 0 means disable";
        units seconds;
      }
    }
  }
  grouping juniper-protocols-msdp {
    leaf data-encapsulation {
      type enumeration {
        enum disable {
          description "Disable data encapsulation";
        }
        enum enable {
          description "Enable data encapsulation";
        }
      }
      description "Set encapsulation of data packets";
    }
    container rib-group {
      description "Routing table group";
      uses rib_group_inet_type;
    }
    container active-source-limit {
      description "Limit the number of active sources accepted";
      leaf maximum {
        type uint32 {
          range "1 .. 1000000";
        }
        default "25000";
        description "Maximum number of active sources accepted";
      }
      leaf threshold {
        type uint32 {
          range "1 .. 1000000";
        }
        default "24000";
        description "RED threshold for active source acceptance";
      }
      leaf log-warning {
        type uint32 {
          range "1 .. 100";
        }
        default "100";
        description "Percentage of maximum at which to start generating warnings";
      }
      leaf log-interval {
        type uint32 {
          range "6 .. 32767";
        }
        description "Time between log messages";
      }
    }
    choice enable-disable {
      case case_1 {
        leaf disable {
          type empty;
          description "Disable MSDP";
        }
      }
    }
    leaf-list export {
      type "jt:policy-algebra";
      description "Export policy";
      ordered-by user;
    }
    leaf-list import {
      type "jt:policy-algebra";
      description "Import policy";
      ordered-by user;
    }
    leaf local-address {
      type "jt:ipv4addr";
      description "Local address";
    }
    container traceoptions {
      description "Trace options for MSDP";
      container file {
        description "Trace file options";
        leaf filename {
          type string {
            length "1 .. 1024";
          }
          description "Name of file in which to write trace information";
        }
        leaf replace {
          type empty;
          description "Replace trace file rather than appending to it";
          status deprecated;
        }
        leaf size {
          type string;
          description "Maximum trace file size";
        }
        leaf files {
          type uint32 {
            range "2 .. 1000";
          }
          default "10";
          description "Maximum number of trace files";
        }
        leaf no-stamp {
          type empty;
          description "Do not timestamp trace file";
          status deprecated;
        }
        choice world-readable-choice {
          leaf world-readable {
            type empty;
            description "Allow any user to read the log file";
          }
          leaf no-world-readable {
            type empty;
            description "Don't allow any user to read the log file";
          }
        }
      }
      list flag {
        description "Tracing parameters";
        key name;
        ordered-by user;
        leaf name {
          type enumeration {
            enum packets {
              description "Trace all MSDP packets";
            }
            enum route {
              description "Trace routing information";
            }
            enum nsr-synchronization {
              description "Trace NSR synchronization events";
            }
            enum source-active {
              description "Trace source-active messages";
            }
            enum source-active-request {
              description "Trace source-active request messages";
            }
            enum source-active-response {
              description "Trace source-active response messages";
            }
            enum keepalive {
              description "Trace keepalive messages";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
        leaf send {
          type empty;
          description "Trace transmitted packets";
        }
        leaf receive {
          type empty;
          description "Trace received packets";
        }
        leaf detail {
          type empty;
          description "Trace detailed information";
        }
        leaf disable {
          type empty;
          description "Disable this trace flag";
        }
      }
    }
    list peer {
      description "Configure an MSDP peer";
      key name;
      ordered-by user;
      leaf name {
        type "jt:ipv4addr";
        description "Peer address";
      }
      choice enable-disable {
        case case_1 {
          leaf disable {
            type empty;
            description "Disable MSDP";
          }
        }
      }
      leaf-list export {
        type "jt:policy-algebra";
        description "Export policy";
        ordered-by user;
      }
      leaf-list import {
        type "jt:policy-algebra";
        description "Import policy";
        ordered-by user;
      }
      leaf local-address {
        type "jt:ipv4addr";
        description "Local address";
      }
      container traceoptions {
        description "Trace options for MSDP";
        container file {
          description "Trace file options";
          leaf filename {
            type string {
              length "1 .. 1024";
            }
            description "Name of file in which to write trace information";
          }
          leaf replace {
            type empty;
            description "Replace trace file rather than appending to it";
            status deprecated;
          }
          leaf size {
            type string;
            description "Maximum trace file size";
          }
          leaf files {
            type uint32 {
              range "2 .. 1000";
            }
            default "10";
            description "Maximum number of trace files";
          }
          leaf no-stamp {
            type empty;
            description "Do not timestamp trace file";
            status deprecated;
          }
          choice world-readable-choice {
            leaf world-readable {
              type empty;
              description "Allow any user to read the log file";
            }
            leaf no-world-readable {
              type empty;
              description "Don't allow any user to read the log file";
            }
          }
        }
        list flag {
          description "Tracing parameters";
          key name;
          ordered-by user;
          leaf name {
            type enumeration {
              enum packets {
                description "Trace all MSDP packets";
              }
              enum route {
                description "Trace routing information";
              }
              enum nsr-synchronization {
                description "Trace NSR synchronization events";
              }
              enum source-active {
                description "Trace source-active messages";
              }
              enum source-active-request {
                description "Trace source-active request messages";
              }
              enum source-active-response {
                description "Trace source-active response messages";
              }
              enum keepalive {
                description "Trace keepalive messages";
              }
              enum normal {
                description "Trace normal events";
              }
              enum general {
                description "Trace general events";
              }
              enum state {
                description "Trace state transitions";
              }
              enum policy {
                description "Trace policy processing";
              }
              enum task {
                description "Trace routing protocol task processing";
              }
              enum timer {
                description "Trace routing protocol timer processing";
              }
              enum all {
                description "Trace everything";
              }
            }
          }
          leaf send {
            type empty;
            description "Trace transmitted packets";
          }
          leaf receive {
            type empty;
            description "Trace received packets";
          }
          leaf detail {
            type empty;
            description "Trace detailed information";
          }
          leaf disable {
            type empty;
            description "Disable this trace flag";
          }
        }
      }
      container active-source-limit {
        description "Limit the number of active sources accepted";
        leaf maximum {
          type uint32 {
            range "1 .. 1000000";
          }
          default "25000";
          description "Maximum number of active sources accepted";
        }
        leaf threshold {
          type uint32 {
            range "1 .. 1000000";
          }
          default "24000";
          description "RED threshold for active source acceptance";
        }
        leaf log-warning {
          type uint32 {
            range "1 .. 100";
          }
          default "100";
          description "Percentage of maximum at which to start generating warnings";
        }
        leaf log-interval {
          type uint32 {
            range "6 .. 32767";
          }
          description "Time between log messages";
        }
      }
      leaf keep-alive {
        type uint32 {
          range "10 .. 60";
        }
        description "Time limit for sending out periodic keep alive to peer";
        units seconds;
      }
      leaf hold-time {
        type uint32 {
          range "15 .. 150";
        }
        description "Max time to terminating a peer for having not received any message from ";
        units seconds;
      }
      leaf sa-hold-time {
        type uint32 {
          range "75 .. 300";
        }
        description "Max time for holding a sa message before timing out";
        units seconds;
      }
      leaf default-peer {
        type empty;
        description "Default RPF peer";
      }
      leaf authentication-key {
        type string {
          length "1 .. 126";
        }
        description "MD5 authentication key";
      }
    }
    leaf keep-alive {
      type uint32 {
        range "10 .. 60";
      }
      description "Time limit for sending out periodic keep alive to peer";
      units seconds;
    }
    leaf hold-time {
      type uint32 {
        range "15 .. 150";
      }
      description "Max time to terminating a peer for having not received any message from ";
      units seconds;
    }
    leaf sa-hold-time {
      type uint32 {
        range "75 .. 300";
      }
      description "Max time for holding a sa message before timing out";
      units seconds;
    }
    list source {
      description "Configure parameters for each source";
      key name;
      ordered-by user;
      leaf name {
        type "jt:ipprefix";
        description "Source address or prefix";
      }
      container active-source-limit {
        description "Limit the number of active sources accepted";
        leaf maximum {
          type uint32 {
            range "1 .. 1000000";
          }
          default "25000";
          description "Maximum number of active sources accepted";
        }
        leaf threshold {
          type uint32 {
            range "1 .. 1000000";
          }
          default "24000";
          description "RED threshold for active source acceptance";
        }
        leaf log-warning {
          type uint32 {
            range "1 .. 100";
          }
          default "100";
          description "Percentage of maximum at which to start generating warnings";
        }
        leaf log-interval {
          type uint32 {
            range "6 .. 32767";
          }
          description "Time between log messages";
        }
      }
    }
    list group {
      description "Configure MSDP peer groups";
      key name;
      ordered-by user;
      leaf name {
        type string;
        description "MSDP peer group name";
      }
      leaf mode {
        type enumeration {
          enum standard {
            description "Use standard MSDP source-active flooding rules";
          }
          enum mesh-group {
            description "Group peers are mesh group members";
          }
        }
        default "standard";
        description "MSDP group source-active flooding mode";
      }
      choice enable-disable {
        case case_1 {
          leaf disable {
            type empty;
            description "Disable MSDP";
          }
        }
      }
      leaf-list export {
        type "jt:policy-algebra";
        description "Export policy";
        ordered-by user;
      }
      leaf-list import {
        type "jt:policy-algebra";
        description "Import policy";
        ordered-by user;
      }
      leaf local-address {
        type "jt:ipv4addr";
        description "Local address";
      }
      container traceoptions {
        description "Trace options for MSDP";
        container file {
          description "Trace file options";
          leaf filename {
            type string {
              length "1 .. 1024";
            }
            description "Name of file in which to write trace information";
          }
          leaf replace {
            type empty;
            description "Replace trace file rather than appending to it";
            status deprecated;
          }
          leaf size {
            type string;
            description "Maximum trace file size";
          }
          leaf files {
            type uint32 {
              range "2 .. 1000";
            }
            default "10";
            description "Maximum number of trace files";
          }
          leaf no-stamp {
            type empty;
            description "Do not timestamp trace file";
            status deprecated;
          }
          choice world-readable-choice {
            leaf world-readable {
              type empty;
              description "Allow any user to read the log file";
            }
            leaf no-world-readable {
              type empty;
              description "Don't allow any user to read the log file";
            }
          }
        }
        list flag {
          description "Tracing parameters";
          key name;
          ordered-by user;
          leaf name {
            type enumeration {
              enum packets {
                description "Trace all MSDP packets";
              }
              enum route {
                description "Trace routing information";
              }
              enum nsr-synchronization {
                description "Trace NSR synchronization events";
              }
              enum source-active {
                description "Trace source-active messages";
              }
              enum source-active-request {
                description "Trace source-active request messages";
              }
              enum source-active-response {
                description "Trace source-active response messages";
              }
              enum keepalive {
                description "Trace keepalive messages";
              }
              enum normal {
                description "Trace normal events";
              }
              enum general {
                description "Trace general events";
              }
              enum state {
                description "Trace state transitions";
              }
              enum policy {
                description "Trace policy processing";
              }
              enum task {
                description "Trace routing protocol task processing";
              }
              enum timer {
                description "Trace routing protocol timer processing";
              }
              enum all {
                description "Trace everything";
              }
            }
          }
          leaf send {
            type empty;
            description "Trace transmitted packets";
          }
          leaf receive {
            type empty;
            description "Trace received packets";
          }
          leaf detail {
            type empty;
            description "Trace detailed information";
          }
          leaf disable {
            type empty;
            description "Disable this trace flag";
          }
        }
      }
      list peer {
        description "Configure an MSDP peer";
        key name;
        ordered-by user;
        leaf name {
          type "jt:ipv4addr";
          description "Peer address";
        }
        choice enable-disable {
          case case_1 {
            leaf disable {
              type empty;
              description "Disable MSDP";
            }
          }
        }
        leaf-list export {
          type "jt:policy-algebra";
          description "Export policy";
          ordered-by user;
        }
        leaf-list import {
          type "jt:policy-algebra";
          description "Import policy";
          ordered-by user;
        }
        leaf local-address {
          type "jt:ipv4addr";
          description "Local address";
        }
        container traceoptions {
          description "Trace options for MSDP";
          container file {
            description "Trace file options";
            leaf filename {
              type string {
                length "1 .. 1024";
              }
              description "Name of file in which to write trace information";
            }
            leaf replace {
              type empty;
              description "Replace trace file rather than appending to it";
              status deprecated;
            }
            leaf size {
              type string;
              description "Maximum trace file size";
            }
            leaf files {
              type uint32 {
                range "2 .. 1000";
              }
              default "10";
              description "Maximum number of trace files";
            }
            leaf no-stamp {
              type empty;
              description "Do not timestamp trace file";
              status deprecated;
            }
            choice world-readable-choice {
              leaf world-readable {
                type empty;
                description "Allow any user to read the log file";
              }
              leaf no-world-readable {
                type empty;
                description "Don't allow any user to read the log file";
              }
            }
          }
          list flag {
            description "Tracing parameters";
            key name;
            ordered-by user;
            leaf name {
              type enumeration {
                enum packets {
                  description "Trace all MSDP packets";
                }
                enum route {
                  description "Trace routing information";
                }
                enum nsr-synchronization {
                  description "Trace NSR synchronization events";
                }
                enum source-active {
                  description "Trace source-active messages";
                }
                enum source-active-request {
                  description "Trace source-active request messages";
                }
                enum source-active-response {
                  description "Trace source-active response messages";
                }
                enum keepalive {
                  description "Trace keepalive messages";
                }
                enum normal {
                  description "Trace normal events";
                }
                enum general {
                  description "Trace general events";
                }
                enum state {
                  description "Trace state transitions";
                }
                enum policy {
                  description "Trace policy processing";
                }
                enum task {
                  description "Trace routing protocol task processing";
                }
                enum timer {
                  description "Trace routing protocol timer processing";
                }
                enum all {
                  description "Trace everything";
                }
              }
            }
            leaf send {
              type empty;
              description "Trace transmitted packets";
            }
            leaf receive {
              type empty;
              description "Trace received packets";
            }
            leaf detail {
              type empty;
              description "Trace detailed information";
            }
            leaf disable {
              type empty;
              description "Disable this trace flag";
            }
          }
        }
        container active-source-limit {
          description "Limit the number of active sources accepted";
          leaf maximum {
            type uint32 {
              range "1 .. 1000000";
            }
            default "25000";
            description "Maximum number of active sources accepted";
          }
          leaf threshold {
            type uint32 {
              range "1 .. 1000000";
            }
            default "24000";
            description "RED threshold for active source acceptance";
          }
          leaf log-warning {
            type uint32 {
              range "1 .. 100";
            }
            default "100";
            description "Percentage of maximum at which to start generating warnings";
          }
          leaf log-interval {
            type uint32 {
              range "6 .. 32767";
            }
            description "Time between log messages";
          }
        }
        leaf keep-alive {
          type uint32 {
            range "10 .. 60";
          }
          description "Time limit for sending out periodic keep alive to peer";
          units seconds;
        }
        leaf hold-time {
          type uint32 {
            range "15 .. 150";
          }
          description "Max time to terminating a peer for having not received any message from ";
          units seconds;
        }
        leaf sa-hold-time {
          type uint32 {
            range "75 .. 300";
          }
          description "Max time for holding a sa message before timing out";
          units seconds;
        }
        leaf default-peer {
          type empty;
          description "Default RPF peer";
        }
        leaf authentication-key {
          type string {
            length "1 .. 126";
          }
          description "MD5 authentication key";
        }
      }
    }
  }
  grouping juniper-protocols-mstp {
    choice enable-disable {
      case case_1 {
        leaf disable {
          type empty;
          description "Disable MSTP";
        }
      }
    }
    leaf bpdu-destination-mac-address {
      type enumeration {
        enum provider-bridge-group {
          description "802.1ad provider bridge group address";
        }
      }
      description "Destination MAC address in the spanning tree BPDUs";
    }
    leaf configuration-name {
      type string {
        length "1 .. 32";
      }
      description "Configuration name (part of MST configuration identifier)";
    }
    leaf revision-level {
      type uint16;
      description "Revision level (part of MST configuration identifier)";
    }
    leaf max-hops {
      type uint16 {
        range "1 .. 255";
      }
      description "Maximum number of hops";
    }
    leaf max-age {
      type uint16 {
        range "6 .. 40";
      }
      description "Maximum age of received protocol bpdu";
      units seconds;
    }
    leaf hello-time {
      type uint16 {
        range "1 .. 10";
      }
      description "Time interval between configuration BPDUs";
      units seconds;
    }
    leaf forward-delay {
      type uint16 {
        range "4 .. 30";
      }
      description "Time spent in listening or learning state";
      units seconds;
    }
    leaf system-identifier {
      type "jt:mac-unicast";
      description "Sytem identifier to represent this node";
    }
    container traceoptions {
      description "Tracing options for debugging protocol operation";
      uses stp-trace-options;
    }
    leaf bridge-priority {
      type string;
      description "Priority of the bridge (in increments of 4k - 0,4k,8k,..60k)";
    }
    leaf backup-bridge-priority {
      type string;
      description "Priority of the bridge (in increments of 4k - 4k,8k,..60k)";
    }
    leaf bpdu-block-on-edge {
      type empty;
      description "Block BPDU on all interfaces configured as edge (BPDU Protect)";
    }
    leaf vpls-flush-on-topology-change {
      type empty;
      description "Enable VPLS MAC flush on root protected CE interface receving topology change";
    }
    leaf priority-hold-time {
      type uint16 {
        range "1 .. 255";
      }
      description "Hold time before switching to primary priority when core domain becomes up";
      units seconds;
    }
    list system-id {
      description "System ID to IP mapping";
      key name;
      ordered-by user;
      uses system-id-ip-map;
    }
    list interface {
      description "Interface options";
      key name;
      uses mstp-interface;
    }
    list msti {
      description "Per-MSTI options";
      key name;
      leaf name {
        type int32 {
          range "1 .. 64";
        }
      }
      leaf bridge-priority {
        type string;
        description "Priority of the bridge (in increments of 4k - 0,4k,8k,..60k)";
      }
      leaf backup-bridge-priority {
        type string;
        description "Priority of the bridge (in increments of 4k - 4k,8k,..60k)";
      }
      leaf-list vlan {
        type string;
        description "VLAN ID or VLAN ID range [1..4094]";
        ordered-by user;
      }
      list interface {
        description "Interface options";
        key name;
        uses mstp-interface;
      }
    }
  }
  grouping juniper-protocols-mvpn {
    description "BGP-MVPN configuration";
    container traceoptions {
      description "Trace options for BGP-MVPN";
      container file {
        description "Trace file options";
        leaf filename {
          type string {
            length "1 .. 1024";
          }
          description "Name of file in which to write trace information";
        }
        leaf replace {
          type empty;
          description "Replace trace file rather than appending to it";
          status deprecated;
        }
        leaf size {
          type string;
          description "Maximum trace file size";
        }
        leaf files {
          type uint32 {
            range "2 .. 1000";
          }
          default "10";
          description "Maximum number of trace files";
        }
        leaf no-stamp {
          type empty;
          description "Do not timestamp trace file";
          status deprecated;
        }
        choice world-readable-choice {
          leaf world-readable {
            type empty;
            description "Allow any user to read the log file";
          }
          leaf no-world-readable {
            type empty;
            description "Don't allow any user to read the log file";
          }
        }
      }
      list flag {
        description "Tracing parameters";
        key name;
        ordered-by user;
        leaf name {
          type enumeration {
            enum error {
              description "Trace errors";
            }
            enum nlri {
              description "Trace MVPN advertisements";
            }
            enum topology {
              description "Trace MVPN topology changes";
            }
            enum tunnel {
              description "Trace provider tunnel events";
            }
            enum umh {
              description "Trace Upstream Multicast Hop (UMH) events";
            }
            enum intra-as-ad {
              description "Trace MVPN intra-AS auto discovery routes";
            }
            enum inter-as-ad {
              description "Trace MVPN inter-AS auto discovery routes";
            }
            enum spmsi-ad {
              description "Trace MVPN SPMSI auto discovery routes";
            }
            enum leaf-ad {
              description "Trace MVPN leaf auto discovery routes";
            }
            enum source-active {
              description "Trace MVPN source active routes";
            }
            enum cmcast-join {
              description "Trace MVPN c-multicast join routes";
            }
            enum mdt-safi-ad {
              description "Trace MVPN MDT SAFI auto discovery routes";
            }
            enum mvpn-limit {
              description "Trace MVPN spmsi and cmcast limit events";
            }
            enum nsr-synchronization {
              description "Trace NSR synchronization events";
            }
            enum route {
              description "Trace routing information";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
        leaf send {
          type empty;
          description "Trace transmitted packets";
        }
        leaf receive {
          type empty;
          description "Trace received packets";
        }
        leaf detail {
          type empty;
          description "Trace detailed information";
        }
        leaf disable {
          type empty;
          description "Disable this trace flag";
        }
      }
    }
    container autodiscovery-only {
      description "Use MVPN exclusively for PE router autodiscovery";
      status deprecated;
      container intra-as {
        description "Intra-AS autodiscovery options";
        leaf inclusive {
          type empty;
          description "Inclusive provider tunnel autodiscovery";
        }
      }
    }
    container family {
      description "BGP-MVPN address family";
      container any {
        description "BGP-MVPN properties for all families";
        presence "enable any";
        leaf disable {
          type empty;
          description "Disable all families";
        }
      }
      container inet {
        description "IPv4 BGP-MVPN properties";
        container autodiscovery-only {
          description "Use MVPN exclusively for PE router autodiscovery";
          container intra-as {
            description "Intra-AS autodiscovery options";
            leaf inclusive {
              type empty;
              description "Inclusive provider tunnel autodiscovery";
            }
          }
        }
        leaf disable {
          type empty;
          description "Disable family IPv4";
        }
      }
      container inet6 {
        description "IPv6 BGP-MVPN properties";
        presence "enable inet6";
        container autodiscovery-only {
          description "Use MVPN exclusively for PE router autodiscovery";
          container intra-as {
            description "Intra-AS autodiscovery options";
            leaf inclusive {
              type empty;
              description "Inclusive provider tunnel autodiscovery";
            }
          }
        }
        leaf disable {
          type empty;
          description "Disable family IPv6";
        }
      }
    }
    choice sender-receiver-site-choice {
      case case_1 {
        leaf receiver-site {
          type empty;
          description "MVPN instance has sites only with multicast receivers";
        }
      }
      case case_2 {
        leaf sender-site {
          type empty;
          description "MVPN instance has sites only with multicast sources";
        }
      }
    }
    leaf unicast-umh-election {
      type empty;
      description "Upstream Multicast Hop election based on unicast route preference";
    }
    container static-umh {
      description "Upstream Multicast Hop election based on static configuration";
      leaf primary {
        type "jt:ipv4addr";
        description "Primary Upstream Multicast Hop";
      }
      leaf backup {
        type "jt:ipv4addr";
        description "Secondary Upstream Multicast Hop";
      }
      choice source-tree_choice {
        case case_1 {
          leaf source-tree {
            type empty;
            description "Mandatory attribute - static-umh applies only to MVPN source-tree c-multicast joins";
          }
        }
      }
    }
    leaf cmcast-joins-limit-inet {
      type uint32 {
        range "0 .. 15000";
      }
      description "Maximum number of cmcast entries for v4";
    }
    leaf cmcast-joins-limit-inet6 {
      type uint32 {
        range "0 .. 15000";
      }
      description "Maximum number of cmcast entries for v6";
    }
    container mvpn-mode {
      description "MVPN mode of operation";
      choice mode {
        case case_1 {
          container rpt-spt {
            description "MVPN works in multicast RPT and SPT mode";
            presence "enable rpt-spt";
            leaf spt-switch-timer {
              type uint32 {
                range "0 .. 60";
              }
              description "Timeout before a PE router switches between RPT and SPT";
              units seconds;
            }
          }
        }
        case case_2 {
          container spt-only {
            description "MVPN works in multicast SPT only mode (default mode)";
            presence "enable spt-only";
            container source-active-advertisement {
              description "Attributes associated with advertising Source-Active A-D routes";
              leaf dampen {
                type uint32 {
                  range "1 .. 30";
                }
                description "Time to wait before re-advertising source-active route";
                units minutes;
              }
              leaf min-rate {
                type string;
                description "Minimum traffic rate required to advertise Source-Active route";
                units "bits per second";
              }
            }
            leaf convert-sa-to-msdp {
              type empty;
              description "Turn on MVPN SA route to MSDP SA conversion";
            }
          }
        }
      }
    }
    container route-target {
      description "Configure route-targets for MVPN routes";
      container import-target {
        description "Target communities used when importing routes";
        container unicast {
          description "Use the same target community as configured for unicast";
          presence "enable unicast";
          choice receiver-sender-target-choice {
            case case_1 {
              leaf receiver {
                type empty;
                description "Target community used when importing receiver site routes";
              }
            }
            case case_2 {
              leaf sender {
                type empty;
                description "Target community used when importing sender site routes";
              }
            }
          }
        }
        container target {
          description "Target community";
          presence "enable target";
          leaf target-value {
            type string;
          }
          choice receiver-sender-target-choice {
            case case_1 {
              leaf receiver {
                type empty;
                description "Target community used when importing receiver site routes";
              }
            }
            case case_2 {
              leaf sender {
                type empty;
                description "Target community used when importing sender site routes";
              }
            }
          }
        }
      }
      container export-target {
        description "Target communities used when exporting routes";
        leaf unicast {
          type empty;
          description "Use the same target community as configured for unicast";
        }
        leaf target {
          type string;
          description "Target community";
        }
      }
    }
    container mvpn-join-load-balance {
      description "MVPN Join Load Balancing Algorithm";
      choice algorithm {
        case case_1 {
          container bytewise-xor-hash {
            description "Upstream selection using bytewise XOR hash";
            presence "enable bytewise-xor-hash";
          }
        }
      }
    }
    leaf install-discard {
      type empty;
      description "Install MVPN discard forwarding entries";
    }
    leaf sender-based-rpf {
      type empty;
      description "Forward multicast traffic only from a selected sender PE";
    }
    container hot-root-standby {
      description "MVPN live-live - hot root standby";
      choice tree {
        case case_1 {
          container source-tree {
            description "MVPN live-live - hot root standby for source tree";
            presence "enable source-tree";
          }
        }
      }
      container min-rate {
        description "Minimum traffic rate for the provider tunnel below which switchover is initiated (in bps)";
        leaf rate {
          type string;
          description "Minium traffic rate for the provider tunnel below which switchover is initiated (in bps)";
          units "bits per second";
        }
        leaf revert-delay {
          type uint32 {
            range "0 .. 20";
          }
          description "Time to delay updating of multicast routes to allow for multicast convergence";
          units seconds;
        }
      }
    }
    leaf hierarchical-nexthop {
      type empty;
      description "Enable hierarchical nexthop usage";
    }
    leaf no-nexthop-sharing-for-selective-tunnel {
      type empty;
      description "Disable Tunnel nexthops from getting shared for selective tunnel";
    }
    container inter-region-template {
      description "MVPN inter-region tunnel mapping template";
      list template {
        description "Define a inter-region template";
        key name;
        ordered-by user;
        leaf name {
          type string;
          description "MVPN Template Name";
        }
        list region {
          description "BGP peer group names used as region";
          key name;
          ordered-by user;
          leaf name {
            type string;
            description "Region name";
          }
          choice tunnel-type {
            case case_1 {
              container rsvp-te {
                description "RSVP-TE point-to-multipoint LSP for flooding";
                choice static-or-dynamic {
                  case case_1 {
                    leaf static-lsp {
                      type string;
                      description "Name of point-to-multipoint LSP";
                    }
                  }
                  case case_2 {
                    container label-switched-path-template {
                      description "Template for dynamic point-to-multipoint LSP parameters";
                      choice dynamic-template {
                        case case_1 {
                          leaf template-name {
                            type string;
                            description "Name of point-to-multipoint LSP template";
                          }
                        }
                        case case_2 {
                          leaf default-template {
                            type empty;
                            description "Use default parameters";
                          }
                        }
                      }
                    }
                  }
                }
              }
            }
            case case_2 {
              container ldp-p2mp {
                description "LDP point-to-multipoint LSP for flooding";
                presence "enable ldp-p2mp";
              }
            }
            case case_3 {
              container ingress-replication {
                description "Ingress replication tunnel";
                leaf create-new-ucast-tunnel {
                  type empty;
                  description "Create new unicast tunnel for ingress replication";
                }
                container label-switched-path {
                  description "Point-to-point LSP unicast tunnel";
                  presence "enable label-switched-path";
                  container label-switched-path-template {
                    description "Template for dynamic point-to-point LSP parameters";
                    choice dynamic-template {
                      case case_1 {
                        leaf template-name {
                          type string;
                          description "Name of point-to-point LSP template";
                        }
                      }
                      case case_2 {
                        leaf default-template {
                          type empty;
                          description "Use default parameters";
                        }
                      }
                    }
                  }
                }
              }
            }
            case case_4 {
              leaf incoming {
                type empty;
                description "Same as incoming provider tunnel";
              }
            }
          }
        }
        container all-regions {
          description "Used for all regions not specified";
          choice tunnel-type {
            case case_1 {
              container rsvp-te {
                description "RSVP-TE point-to-multipoint LSP for flooding";
                choice static-or-dynamic {
                  case case_1 {
                    leaf static-lsp {
                      type string;
                      description "Name of point-to-multipoint LSP";
                    }
                  }
                  case case_2 {
                    container label-switched-path-template {
                      description "Template for dynamic point-to-multipoint LSP parameters";
                      choice dynamic-template {
                        case case_1 {
                          leaf template-name {
                            type string;
                            description "Name of point-to-multipoint LSP template";
                          }
                        }
                        case case_2 {
                          leaf default-template {
                            type empty;
                            description "Use default parameters";
                          }
                        }
                      }
                    }
                  }
                }
              }
            }
            case case_2 {
              container ldp-p2mp {
                description "LDP point-to-multipoint LSP for flooding";
                presence "enable ldp-p2mp";
              }
            }
            case case_3 {
              container ingress-replication {
                description "Ingress replication tunnel";
                leaf create-new-ucast-tunnel {
                  type empty;
                  description "Create new unicast tunnel for ingress replication";
                }
                container label-switched-path {
                  description "Point-to-point LSP unicast tunnel";
                  presence "enable label-switched-path";
                  container label-switched-path-template {
                    description "Template for dynamic point-to-point LSP parameters";
                    choice dynamic-template {
                      case case_1 {
                        leaf template-name {
                          type string;
                          description "Name of point-to-point LSP template";
                        }
                      }
                      case case_2 {
                        leaf default-template {
                          type empty;
                          description "Use default parameters";
                        }
                      }
                    }
                  }
                }
              }
            }
            case case_4 {
              leaf incoming {
                type empty;
                description "Same as incoming provider tunnel";
              }
            }
          }
        }
      }
    }
    leaf source-redundancy {
      type empty;
      description "Assume all the sources for a particular group is sending same data";
    }
    container umh-selection-additional-input {
      description "Additional parameters to consider during UMH";
      leaf source-active-preference {
        type empty;
        description "Use the preference set in the source active route";
      }
      leaf tunnel-status {
        type empty;
        description "Use the RSVP tunnel status";
      }
    }
  }
  grouping juniper-protocols-mvrp {
    description "MVRP Configuration";
    container traceoptions {
      description "Tracing options for MVRP";
      uses mrp-trace-options;
    }
    leaf join-timer {
      type uint16 {
        range "100 .. 500";
      }
      default "200";
      description "Join timer interval";
      units milliseconds;
    }
    leaf leave-timer {
      type uint16 {
        range "300 .. 1000";
      }
      default "800";
      description "Leave timer interval";
      units milliseconds;
    }
    leaf leaveall-timer {
      type uint16 {
        range "10 .. 60";
      }
      default "10";
      description "Leaveall timer interval";
      units seconds;
    }
    leaf no-dynamic-vlan {
      type empty;
      description "Disable dynamic VLAN creation";
    }
    leaf no-attribute-length-in-pdu {
      type empty;
      description "No attribute length while sending pdu ";
    }
    leaf bpdu-destination-mac-address {
      type enumeration {
        enum provider-bridge-group {
          description "802.1ad provider bridge group address";
        }
      }
      description "Destination MAC address in the MVRP BPDUs";
    }
    list interface {
      description "Configure interface options";
      key name;
      ordered-by user;
      leaf name {
        type "jt:interface-device";
        description "Interface name";
      }
      leaf join-timer {
        type uint16 {
          range "100 .. 500";
        }
        description "Join timer interval";
        units milliseconds;
      }
      leaf leave-timer {
        type uint16 {
          range "300 .. 1000";
        }
        description "Leave timer interval";
        units milliseconds;
      }
      leaf leaveall-timer {
        type uint16 {
          range "10 .. 60";
        }
        description "Leaveall timer interval";
        units seconds;
      }
      leaf point-to-point {
        type empty;
        description "Port is point to point";
      }
      leaf registration {
        type enumeration {
          enum normal {
            description "Normal registration mode";
          }
          enum restricted {
            description "Restricted registration mode";
          }
          enum forbidden {
            description "Forbidden registration mode";
          }
        }
        default "normal";
        description "Registration mode";
      }
    }
  }
  grouping juniper-protocols-openflow {
    list switch {
      description "OpenFlow switch";
      key name;
      max-elements 1;
      ordered-by user;
      leaf name {
        type string {
          length "1 .. 64";
        }
        description "Switch name";
      }
      container default-action {
        description "Action for packets that not have a matching flow entry";
        choice drop-pktin {
          case case_1 {
            leaf drop {
              type empty;
              description "Drop all packets that do not have a matching flow entry";
            }
          }
          case case_2 {
            leaf packet-in {
              type empty;
              description "Send packets to client if no matching flow entry";
            }
          }
        }
      }
      list interfaces {
        description "Interfaces configured for use with Openflow";
        key name;
        ordered-by user;
        leaf name {
          type "jt:interface-name";
          description "Interface name";
        }
        leaf port-id {
          type int32 {
            range "1 .. 32640";
          }
          description "Openflow port ID";
        }
      }
      leaf purge-flow-timer {
        type uint32 {
          range "0 .. 300";
        }
        description "Purge timer value for invalid flows";
        units seconds;
      }
      container controller {
        description "OpenFlow controller's IP address, port and protocol";
        container protocol {
          description "Protocol type for controller connection";
          container tcp {
            description "Set protocol type to 'TCP' (default)";
            leaf port {
              type int32 {
                range "1024 .. 65535";
              }
              description "Controller's port number (default 6633)";
            }
          }
        }
        leaf role {
          type enumeration {
            enum equal {
              description "Set role to 'equal'";
            }
          }
          description "Controller role";
        }
        leaf address {
          type "jt:ipaddr";
          description "Controller's IPv4 address";
        }
        leaf id {
          type uint32;
          description "Controller id";
        }
      }
    }
    container traceoptions {
      description "OpenFlow switch daemon trace options";
      leaf no-remote-trace {
        type empty;
        description "Disable remote tracing";
      }
      container file {
        description "Trace file information";
        leaf filename {
          type string {
            length "1 .. 1024";
          }
          description "Name of file in which to write trace information";
        }
        leaf size {
          type string;
          description "Maximum trace file size";
        }
        leaf files {
          type uint32 {
            range "2 .. 1000";
          }
          default "3";
          description "Maximum number of trace files";
        }
        choice world-readable-choice {
          leaf world-readable {
            type empty;
            description "Allow any user to read the log file";
          }
          leaf no-world-readable {
            type empty;
            description "Don't allow any user to read the log file";
          }
        }
        leaf match {
          type "jt:regular-expression";
          description "Regular expression for lines to be logged";
        }
      }
      list flag {
        description "Tracing flag parameters";
        key name;
        ordered-by user;
        leaf name {
          type enumeration {
            enum switch {
              description "Trace openflow switch events";
            }
            enum configuration {
              description "Trace openflow configuration events";
            }
            enum flow {
              description "Trace openflow flow events";
            }
            enum filter {
              description "Trace openflow filter events";
            }
            enum function {
              description "Trace openflow function entry/exit events";
            }
            enum packet-io {
              description "Trace openflow packet in/out events";
            }
            enum statistics {
              description "Trace openflow statistics events";
            }
            enum interface {
              description "Trace openflow interface events";
            }
            enum packets {
              description "Trace openflow packets";
            }
            enum barrier {
              description "Trace openflow barrier events";
            }
            enum nh {
              description "Trace openflow next-hop events";
            }
            enum group {
              description "Trace openflow group events";
            }
            enum all {
              description "Trace everything";
            }
          }
        }
      }
    }
  }
  grouping juniper-protocols-ospf {
    list topology {
      description "Topology parameters";
      key name;
      ordered-by user;
      leaf name {
        type string;
        description "Topology name";
      }
      leaf disable {
        type empty;
        description "Disable this topology";
      }
      leaf topology-id {
        type uint8 {
          range "32 .. 127";
        }
        description "Topology identifier";
      }
      leaf overload {
        type empty;
        description "Set the overload mode (repel transit traffic)";
      }
      leaf rib-group {
        type string;
        description "Routing table group for importing routes";
      }
      container spf-options {
        description "Configure options for SPF";
        container microloop-avoidance {
          description "Configure microloop avoidance mechanism";
          container post-convergence-path {
            description "Temporarily install post-convergence path for routes potentially affected by microloops";
            presence "enable post-convergence-path";
            leaf delay {
              type uint32 {
                range "500 .. 60000";
              }
              description "Time after which temporary post-convergence paths are removed";
              units milliseconds;
            }
            leaf maximum-labels {
              type uint32 {
                range "2 .. 8";
              }
              description "Maximum number of labels installed for post-convergence paths";
            }
          }
        }
        leaf delay {
          type uint32 {
            range "50 .. 8000";
          }
          description "Time to wait before running an SPF";
          units milliseconds;
        }
        leaf holddown {
          type uint32 {
            range "2000 .. 20000";
          }
          description "Time to hold down before running an SPF";
          units milliseconds;
        }
        leaf rapid-runs {
          type uint32 {
            range "1 .. 10";
          }
          description "Number of maximum rapid SPF runs before holddown";
        }
        leaf no-ignore-our-externals {
          type empty;
          description "Do not ignore self-generated external and NSSA LSAs";
        }
      }
      container backup-spf-options {
        description "Configure options for backup SPF";
        container remote-backup-calculation {
          description "Calculate Remote LFA backup nexthops";
          presence "enable remote-backup-calculation";
          container pq-nodes-nearest-to-source {
            description "PQ nodes selection based upon nearest to source";
            leaf percent {
              type uint32 {
                range "10 .. 100";
              }
              description "Selection percentage for nearest to source";
            }
          }
        }
        container use-post-convergence-lfa {
          description "Calculate post-convergence backup paths";
          presence "enable use-post-convergence-lfa";
          leaf maximum-labels {
            type uint32 {
              range "2 .. 8";
            }
            description "Maximum number of labels installed for post-convergence paths";
          }
          leaf maximum-backup-paths {
            type uint32 {
              range "1 .. 8";
            }
            description "Maximum number of equal-cost post-convergence paths installed";
          }
        }
        leaf use-source-packet-routing {
          type empty;
          description "Use spring backup paths for inet.0 routes";
        }
        leaf disable {
          type empty;
          description "Do not run backup SPF";
        }
        leaf no-install {
          type empty;
          description "Do not install backup nexthops into the RIB";
        }
        leaf downstream-paths-only {
          type empty;
          description "Use only downstream backup paths";
        }
        container per-prefix-calculation {
          description "Calculate backup nexthops for non-best prefix originators";
          leaf stubs {
            type empty;
            description "Per prefix calculation for stubs only";
          }
          leaf summary {
            type empty;
            description "Per prefix calculation for summary originators only";
          }
          leaf externals {
            type empty;
            description "Per prefix calculation for externals";
          }
          leaf all {
            type empty;
            description "Per prefix calculation for all";
          }
        }
        leaf node-link-degradation {
          type empty;
          description "Degrade to link protection when nodelink protection not available";
        }
      }
      leaf prefix-export-limit {
        type uint32 {
          range "0 .. 4294967295";
        }
        description "Maximum number of prefixes that can be exported";
      }
    }
    container spf-options {
      description "Configure options for SPF";
      container microloop-avoidance {
        description "Configure microloop avoidance mechanism";
        container post-convergence-path {
          description "Temporarily install post-convergence path for routes potentially affected by microloops";
          presence "enable post-convergence-path";
          leaf delay {
            type uint32 {
              range "500 .. 60000";
            }
            description "Time after which temporary post-convergence paths are removed";
            units milliseconds;
          }
          leaf maximum-labels {
            type uint32 {
              range "2 .. 8";
            }
            description "Maximum number of labels installed for post-convergence paths";
          }
        }
      }
      leaf delay {
        type uint32 {
          range "50 .. 8000";
        }
        description "Time to wait before running an SPF";
        units milliseconds;
      }
      leaf holddown {
        type uint32 {
          range "2000 .. 20000";
        }
        description "Time to hold down before running an SPF";
        units milliseconds;
      }
      leaf rapid-runs {
        type uint32 {
          range "1 .. 10";
        }
        description "Number of maximum rapid SPF runs before holddown";
      }
      leaf no-ignore-our-externals {
        type empty;
        description "Do not ignore self-generated external and NSSA LSAs";
      }
    }
    container backup-spf-options {
      description "Configure options for backup SPF";
      container remote-backup-calculation {
        description "Calculate Remote LFA backup nexthops";
        presence "enable remote-backup-calculation";
        container pq-nodes-nearest-to-source {
          description "PQ nodes selection based upon nearest to source";
          leaf percent {
            type uint32 {
              range "10 .. 100";
            }
            description "Selection percentage for nearest to source";
          }
        }
      }
      container use-post-convergence-lfa {
        description "Calculate post-convergence backup paths";
        presence "enable use-post-convergence-lfa";
        leaf maximum-labels {
          type uint32 {
            range "2 .. 8";
          }
          description "Maximum number of labels installed for post-convergence paths";
        }
        leaf maximum-backup-paths {
          type uint32 {
            range "1 .. 8";
          }
          description "Maximum number of equal-cost post-convergence paths installed";
        }
      }
      leaf use-source-packet-routing {
        type empty;
        description "Use spring backup paths for inet.0 routes";
      }
      leaf disable {
        type empty;
        description "Do not run backup SPF";
      }
      leaf no-install {
        type empty;
        description "Do not install backup nexthops into the RIB";
      }
      leaf downstream-paths-only {
        type empty;
        description "Use only downstream backup paths";
      }
      container per-prefix-calculation {
        description "Calculate backup nexthops for non-best prefix originators";
        leaf stubs {
          type empty;
          description "Per prefix calculation for stubs only";
        }
        leaf summary {
          type empty;
          description "Per prefix calculation for summary originators only";
        }
        leaf externals {
          type empty;
          description "Per prefix calculation for externals";
        }
        leaf all {
          type empty;
          description "Per prefix calculation for all";
        }
      }
      leaf node-link-degradation {
        type empty;
        description "Degrade to link protection when nodelink protection not available";
      }
    }
    container traffic-engineering {
      description "Configure traffic engineering attributes";
      presence "enable traffic-engineering";
      leaf no-topology {
        type empty;
        description "Disable dissemination of TE link-state topology information";
      }
      leaf multicast-rpf-routes {
        type empty;
        description "Install routes for multicast RPF checks into inet.2";
      }
      leaf l3-unicast-topology {
        type empty;
        description "Download IGP topology into TED";
      }
      container ignore-lsp-metrics {
        description "Ignore label-switched path metrics when doing shortcuts";
        presence "enable ignore-lsp-metrics";
        leaf unconfigured-only {
          type empty;
          description "Ignore lsp metrics for unconfigured only";
        }
      }
      container shortcuts {
        description "Use label-switched paths as next hops, if possible";
        presence "enable shortcuts";
        leaf ignore-lsp-metrics {
          type empty;
          description "Ignore label-switched path metrics when doing shortcuts";
          status deprecated;
        }
        leaf lsp-metric-into-summary {
          type empty;
          description "Advertise LSP metric into summary LSAs";
        }
        list family {
          description "Address family specific traffic-engineering attributes";
          key name;
          ordered-by user;
          leaf name {
            type enumeration {
              enum inet {
                description "IPv4 family";
              }
              enum inet-mpls {
                description "IPv4-MPLS family";
              }
            }
          }
        }
      }
      leaf advertise-unnumbered-interfaces {
        type empty;
        description "Advertise unnumbered interfaces";
      }
      leaf credibility-protocol-preference {
        type empty;
        description "TED protocol credibility follows protocol preference";
      }
      container advertisement {
        description "Advertise TE parameters even if RSVP is not turned on";
        leaf always {
          type empty;
          description "Advertise TE parameters in TE LSAs";
        }
      }
      container tunnel-source-protocol {
        description "Protocols from which to pick label-switched paths";
        container rsvp {
          description "Pick label-switched paths from rsvp";
          presence "enable rsvp";
          leaf preference {
            type uint32 {
              range "1 .. 255";
            }
            description "Preference for label-switched paths from this protocol";
          }
        }
        container spring-te {
          description "Pick label-switched paths from spring-te";
          presence "enable spring-te";
          leaf preference {
            type uint32 {
              range "1 .. 255";
            }
            description "Preference for label-switched paths from this protocol";
          }
        }
      }
    }
    container source-packet-routing {
      description "Enable source packet routing (SPRING)";
      presence "enable source-packet-routing";
      container adjacency-segment {
        description "Attributes for adjacency segments in spring";
        leaf hold-time {
          type uint32 {
            range "180000 .. 900000";
          }
          description "Retain time of Adjacency segment after isolating from an interface";
        }
      }
      leaf-list prefix-segment {
        type "jt:policy-algebra";
        description "Prefix Segment policy";
        ordered-by user;
      }
      leaf explicit-null {
        type empty;
        description "Set E and P bits in all Prefix SID advertisements";
      }
      container node-segment {
        description "Enable support for Node segments in SPRING";
        presence "enable node-segment";
        leaf ipv4-index {
          type uint32 {
            range "0 .. 199999";
          }
          description "Set ipv4 node segment index";
        }
        leaf index-range {
          type uint32 {
            range "32 .. 16385";
          }
          description "Set range of node segment indices allowed";
        }
      }
      container srgb {
        description "Set the SRGB global block in SPRING";
        leaf start-label {
          type uint32;
          description "Start range for SRGB label block";
        }
        leaf index-range {
          type uint32;
          description "Index to the SRGB start label block";
        }
      }
      leaf mapping-server {
        type string;
        description "Mapping server name";
      }
      leaf install-prefix-sid-for-best-route {
        type empty;
        description "For best route install a exact prefix sid route";
      }
      leaf ldp-stitching {
        type empty;
        description "Enable SR to LDP stitching";
      }
      leaf-list flex-algorithm {
        type uint32 {
          range "128 .. 255";
        }
        description "Flex-algorithms we would like to participate in";
        max-elements 16;
      }
      leaf strict-asla-based-flex-algorithm {
        type empty;
        description "Flex-Algorithm to ignore links not having ASLA sub-TLVs";
      }
      container sensor-based-stats {
        description "Configure sensor based stats in SPRING";
        container per-interface-per-member-link {
          description "Configure sensor based stats per nexthop";
          leaf ingress {
            type empty;
            description "Enable sensor based stats on ingress interface";
          }
          leaf egress {
            type empty;
            description "Enable sensor based stats on egress interface";
          }
        }
        container per-sid {
          description "Configure sensor based stats per spring route";
          leaf ingress {
            type empty;
            description "Enable sensor based stats for per-sid ingress accounting";
          }
          leaf egress {
            type empty;
            description "Enable sensor based stats for IP-MPLS egress accounting";
          }
        }
      }
    }
    list area {
      description "Configure an OSPF area";
      key name;
      ordered-by user;
      leaf name {
        type "jt:areaid";
        description "Area ID";
      }
      choice stub-option {
        case case_1 {
          container stub {
            description "Configure a stub area";
            presence "enable stub";
            leaf default-metric {
              type uint32 {
                range "1 .. 16777215";
              }
              description "Metric for the default route in this stub area";
            }
            choice summaries-choice {
              leaf summaries {
                type empty;
                description "Flood summary LSAs into this stub area";
              }
              leaf no-summaries {
                type empty;
                description "Don't flood summary LSAs into this stub area";
              }
            }
          }
        }
        case case_2 {
          container nssa {
            description "Configure a not-so-stubby area";
            presence "enable nssa";
            container default-lsa {
              description "Configure a default LSA";
              presence "enable default-lsa";
              leaf default-metric {
                type uint32 {
                  range "1 .. 16777215";
                }
                description "Metric for the default route in this area";
              }
              leaf metric-type {
                type uint32 {
                  range "1 .. 2";
                }
                description "External metric type for the default type 7 LSA";
              }
              leaf type-7 {
                type empty;
                description "Flood type 7 default LSA if no-summaries is configured";
              }
            }
            leaf default-metric {
              type uint32 {
                range "1 .. 16777215";
              }
              description "Metric for the default route in this area";
              status deprecated;
            }
            leaf metric-type {
              type uint32 {
                range "1 .. 2";
              }
              description "External metric type for the default type 7 LSA";
              status deprecated;
            }
            choice summaries-choice {
              leaf summaries {
                type empty;
                description "Flood summary LSAs into this NSSA area";
              }
              leaf no-summaries {
                type empty;
                description "Don't flood summary LSAs into this NSSA area";
              }
            }
            list area-range {
              description "Configure NSSA area ranges";
              key name;
              ordered-by user;
              leaf name {
                type "jt:ipprefix";
                description "Range to summarize NSSA routes in this area";
              }
              leaf restrict {
                type empty;
                description "Restrict advertisement of this area range";
              }
              leaf exact {
                type empty;
                description "Enforce exact match for advertisement of this area range";
              }
              container override-metric {
                description "Override the dynamic metric for this area-range";
                presence "enable override-metric";
                leaf metric {
                  type uint32 {
                    range "1 .. 16777215";
                  }
                  description "Metric value";
                }
                leaf metric-type {
                  type uint32 {
                    range "1 .. 2";
                  }
                  default "1";
                  description "Set the metric type for the override metric";
                }
              }
            }
          }
        }
      }
      list area-range {
        description "Configure area ranges";
        key name;
        ordered-by user;
        leaf name {
          type "jt:ipprefix";
          description "Range to summarize routes in this area";
        }
        leaf restrict {
          type empty;
          description "Restrict advertisement of this area range";
        }
        leaf exact {
          type empty;
          description "Enforce exact match for advertisement of this area range";
        }
        leaf override-metric {
          type uint32 {
            range "1 .. 16777215";
          }
          description "Override the dynamic metric for this area-range";
        }
      }
      leaf-list network-summary-export {
        type "jt:policy-algebra";
        description "Export policy for Type 3 Summary LSAs";
        ordered-by user;
      }
      leaf-list network-summary-import {
        type "jt:policy-algebra";
        description "Import policy for Type 3 Summary LSAs";
        ordered-by user;
      }
      leaf-list inter-area-prefix-export {
        type "jt:policy-algebra";
        description "Export policy for Inter Area Prefix LSAs";
        ordered-by user;
      }
      leaf-list inter-area-prefix-import {
        type "jt:policy-algebra";
        description "Import policy for Inter Area Prefix LSAs";
        ordered-by user;
      }
      leaf authentication-type {
        type enumeration {
          enum none {
            description "No authentication";
            status deprecated;
          }
          enum simple {
            description "Simple password authentication";
            status deprecated;
          }
          enum md5 {
            description "MD5 authentication";
            status deprecated;
          }
        }
        description "Authentication type";
        status deprecated;
      }
      list virtual-link {
        description "Configure virtual links";
        key "neighbor-id transit-area";
        ordered-by user;
        leaf neighbor-id {
          type "jt:ipv4addr";
          description "Router ID of a virtual neighbor";
        }
        leaf transit-area {
          type "jt:areaid";
          description "Transit area in common with virtual neighbor";
        }
        choice enable-disable {
          case case_1 {
            leaf disable {
              type empty;
              description "Disable this virtual link";
            }
          }
        }
        leaf retransmit-interval {
          type uint32 {
            range "1 .. 65535";
          }
          description "Retransmission interval (seconds)";
        }
        leaf transit-delay {
          type uint32 {
            range "1 .. 65535";
          }
          description "Transit delay (seconds)";
        }
        leaf hello-interval {
          type uint32 {
            range "1 .. 255";
          }
          description "Hello interval (seconds)";
        }
        leaf dead-interval {
          type uint32 {
            range "1 .. 65535";
          }
          description "Dead interval (seconds)";
        }
        leaf mtu {
          type uint32 {
            range "128 .. 65535";
          }
          description "Maximum OSPF packet size";
        }
        choice auth {
          case case_1 {
            container authentication {
              uses juniper-ospf-authentication;
            }
          }
          case case_2 {
            container authentication-key {
              description "Authentication key";
              status deprecated;
              leaf keyname {
                type "jt:unreadable";
                description "Authentication key value";
              }
              leaf key-id {
                type uint32 {
                  range "0 .. 255";
                }
                description "Key ID for MD5 authentication";
              }
            }
          }
        }
        leaf demand-circuit {
          type empty;
          description "Interface functions as a demand circuit";
        }
        leaf flood-reduction {
          type empty;
          description "Enable flood reduction";
        }
        leaf no-neighbor-down-notification {
          type empty;
          description "Don't inform other protocols about neighbor down events";
        }
        leaf ipsec-sa {
          type string {
            length "1 .. 32";
          }
          description "IPSec security association name";
        }
        list topology {
          description "Topology specific attributes";
          key name;
          ordered-by user;
          leaf name {
            type string;
            description "Topology name";
          }
          leaf disable {
            type empty;
            description "Disable this topology";
          }
          leaf metric {
            type uint16 {
              range "1 .. 65535";
            }
            description "Topology metric";
          }
          container bandwidth-based-metrics {
            description "Configure bandwidth based metrics";
            list bandwidth {
              description "Bandwidth threshold";
              key name;
              leaf name {
                type string;
              }
              leaf metric {
                type uint16 {
                  range "1 .. 65535";
                }
                description "Metric associated with specified bandwidth";
              }
            }
          }
        }
      }
      list sham-link-remote {
        description "Configure parameters for remote sham link endpoint";
        key name;
        ordered-by user;
        leaf name {
          type "jt:ipaddr";
          description "Remote sham link endpoint address";
        }
        leaf metric {
          type uint16 {
            range "1 .. 65535";
          }
          description "Sham link metric";
        }
        leaf ipsec-sa {
          type string {
            length "1 .. 32";
          }
          description "IPSec security association name";
        }
        leaf demand-circuit {
          type empty;
          description "Interface functions as a demand circuit";
        }
        leaf flood-reduction {
          type empty;
          description "Enable flood reduction";
        }
        list topology {
          description "Topology specific attributes";
          key name;
          ordered-by user;
          leaf name {
            type string;
            description "Topology name";
          }
          leaf disable {
            type empty;
            description "Disable this topology";
          }
          leaf metric {
            type uint16 {
              range "1 .. 65535";
            }
            description "Topology metric";
          }
          container bandwidth-based-metrics {
            description "Configure bandwidth based metrics";
            list bandwidth {
              description "Bandwidth threshold";
              key name;
              leaf name {
                type string;
              }
              leaf metric {
                type uint16 {
                  range "1 .. 65535";
                }
                description "Metric associated with specified bandwidth";
              }
            }
          }
        }
      }
      list interface {
        description "Include an interface in this area";
        key name;
        ordered-by user;
        leaf name {
          type "jt:ipv4addr-or-interface";
          description "Interface name";
        }
        choice enable-disable {
          case case_1 {
            leaf disable {
              type empty;
              description "Disable OSPF on this interface";
            }
          }
        }
        leaf interface-type {
          type enumeration {
            enum nbma {
              description "Nonbroadcast multiaccess";
            }
            enum p2mp {
              description "Point-to-multipoint NBMA";
            }
            enum p2p {
              description "Point-to-point";
            }
            enum p2mp-over-lan {
              description "Point-to-multipoint over LAN mode";
            }
          }
          description "Type of interface";
        }
        choice protection-type {
          case case_1 {
            leaf link-protection {
              type empty;
              description "Protect interface from link faults only";
            }
          }
          case case_2 {
            leaf node-link-protection {
              type empty;
              description "Protect interface from both link and node faults";
            }
          }
        }
        leaf no-eligible-backup {
          type empty;
          description "Not eligible to backup traffic from protected interfaces";
        }
        leaf no-eligible-remote-backup {
          type empty;
          description "Not eligible for Remote-LFA backup traffic from protected interfaces";
        }
        container passive {
          description "Do not run OSPF, but advertise it";
          presence "enable passive";
          container traffic-engineering {
            description "Advertise TE link information";
            leaf remote-node-id {
              type "jt:ipaddr";
              description "Remote address of the link";
            }
            leaf remote-node-router-id {
              type "jt:ipv4addr";
              description "TE Router-ID of the remote node";
            }
          }
        }
        leaf secondary {
          type empty;
          description "Treat interface as secondary";
        }
        leaf own-router-lsa {
          type empty;
          description "Generate a separate router LSA for this interface";
        }
        container bandwidth-based-metrics {
          description "Configure bandwidth based metrics";
          list bandwidth {
            description "Bandwidth threshold";
            key name;
            leaf name {
              type string;
            }
            leaf metric {
              type uint16 {
                range "1 .. 65535";
              }
              description "Metric associated with specified bandwidth";
            }
          }
        }
        leaf metric {
          type uint16 {
            range "1 .. 65535";
          }
          description "Interface metric";
        }
        leaf priority {
          type uint32 {
            range "0 .. 255";
          }
          description "Designated router priority";
        }
        leaf retransmit-interval {
          type uint32 {
            range "1 .. 65535";
          }
          description "Retransmission interval (seconds)";
        }
        leaf transit-delay {
          type uint32 {
            range "1 .. 65535";
          }
          description "Transit delay (seconds)";
        }
        leaf hello-interval {
          type uint32 {
            range "1 .. 255";
          }
          description "Hello interval (seconds)";
        }
        leaf dead-interval {
          type uint32 {
            range "1 .. 65535";
          }
          description "Dead interval (seconds)";
        }
        leaf mtu {
          type uint32 {
            range "128 .. 65535";
          }
          description "Maximum OSPF packet size";
        }
        choice auth {
          case case_1 {
            container authentication {
              uses juniper-ospf-authentication;
            }
          }
          case case_2 {
            container authentication-key {
              description "Authentication key";
              status deprecated;
              leaf keyname {
                type "jt:unreadable";
                description "Authentication key value";
              }
              leaf key-id {
                type uint32 {
                  range "0 .. 255";
                }
                description "Key ID for MD5 authentication";
              }
            }
          }
        }
        leaf demand-circuit {
          type empty;
          description "Interface functions as a demand circuit";
        }
        leaf flood-reduction {
          type empty;
          description "Enable flood reduction";
        }
        leaf no-neighbor-down-notification {
          type empty;
          description "Don't inform other protocols about neighbor down events";
        }
        leaf ipsec-sa {
          type string {
            length "1 .. 32";
          }
          description "IPSec security association name";
        }
        list topology {
          description "Topology specific attributes";
          key name;
          ordered-by user;
          leaf name {
            type string;
            description "Topology name";
          }
          leaf disable {
            type empty;
            description "Disable this topology";
          }
          leaf metric {
            type uint16 {
              range "1 .. 65535";
            }
            description "Topology metric";
          }
          container bandwidth-based-metrics {
            description "Configure bandwidth based metrics";
            list bandwidth {
              description "Bandwidth threshold";
              key name;
              leaf name {
                type string;
              }
              leaf metric {
                type uint16 {
                  range "1 .. 65535";
                }
                description "Metric associated with specified bandwidth";
              }
            }
          }
        }
        leaf transmit-interval {
          type uint32 {
            range "1 .. 4294967295";
          }
          description "OSPF packet transmit interval (milliseconds)";
          status deprecated;
        }
        container bfd-liveness-detection {
          description "Bidirectional Forwarding Detection options";
          leaf version {
            type enumeration {
              enum 0 {
                description "BFD version 0 (deprecated)";
              }
              enum 1 {
                description "BFD version 1";
              }
              enum automatic {
                description "Choose BFD version automatically";
              }
            }
            default "automatic";
            description "BFD protocol version number";
          }
          leaf minimum-interval {
            type uint32 {
              range "1 .. 255000";
            }
            description "Minimum transmit and receive interval";
            units milliseconds;
          }
          leaf minimum-transmit-interval {
            type uint32 {
              range "1 .. 255000";
            }
            description "Minimum transmit interval";
            status deprecated;
            units milliseconds;
          }
          leaf minimum-receive-interval {
            type uint32 {
              range "1 .. 255000";
            }
            description "Minimum receive interval";
            units milliseconds;
          }
          leaf multiplier {
            type uint32 {
              range "1 .. 255";
            }
            default "3";
            description "Detection time multiplier";
          }
          leaf inline-disable {
            type empty;
            description "Disable inline mode for this BFD session";
          }
          leaf pdu-size {
            type uint32 {
              range "24 .. 9000";
            }
            default "24";
            description "BFD transport protocol payload size";
          }
          choice adaptation-choice {
            case case_1 {
              leaf no-adaptation {
                type empty;
                description "Disable adaptation";
              }
            }
          }
          container transmit-interval {
            description "Transmit-interval options";
            leaf minimum-interval {
              type uint32 {
                range "1 .. 255000";
              }
              description "Minimum transmit interval";
              units milliseconds;
            }
            leaf threshold {
              type uint32;
              description "High transmit interval triggering a trap";
              units milliseconds;
            }
          }
          container detection-time {
            description "Detection-time options";
            leaf threshold {
              type uint32;
              description "High detection-time triggering a trap";
              units milliseconds;
            }
          }
          container authentication {
            description "Authentication options";
            leaf key-chain {
              type string;
              description "Key chain name";
            }
            leaf algorithm {
              type enumeration {
                enum simple-password {
                  description "Simple password";
                }
                enum keyed-md5 {
                  description "Keyed message Digest 5";
                }
                enum meticulous-keyed-md5 {
                  description "Meticulous keyed message Digest 5";
                }
                enum keyed-sha-1 {
                  description "Keyed secure hash algorithm (SHA1) ";
                }
                enum meticulous-keyed-sha-1 {
                  description "Meticulous keyed secure hash algorithm (SHA1) ";
                }
              }
              description "Algorithm name";
            }
            leaf loose-check {
              type empty;
              description "Verify authentication only if authentication is negotiated";
            }
          }
          container echo {
            description "Echo mode parameters";
            leaf minimum-interval {
              type uint32 {
                range "100 .. 255000";
              }
              description "Minimum transmit and receive interval";
              units milliseconds;
            }
          }
          container echo-lite {
            description "Echo-lite more parameters";
            leaf minimum-interval {
              type uint32 {
                range "100 .. 255000";
              }
              description "Minimum transmit and receive interval";
              units milliseconds;
            }
          }
          leaf full-neighbors-only {
            type empty;
            description "Setup BFD sessions only to Full neighbors";
          }
          leaf holddown-interval {
            type uint32 {
              range "0 .. 255000";
            }
            description "Time to hold the session-UP notification to the client";
            units milliseconds;
          }
        }
        leaf dynamic-neighbors {
          type empty;
          description "Learn neighbors dynamically on a p2mp interface";
        }
        leaf no-advertise-adjacency-segment {
          type empty;
          description "Do not advertise an adjacency segment for this interface";
        }
        list neighbor {
          description "NBMA neighbor";
          key name;
          ordered-by user;
          leaf name {
            type "jt:ipaddr";
            description "Address of neighbor";
          }
          leaf eligible {
            type empty;
            description "Eligible to be DR on an NBMA network";
          }
        }
        leaf poll-interval {
          type uint32 {
            range "1 .. 65535";
          }
          description "Poll interval for NBMA interfaces";
        }
        leaf no-interface-state-traps {
          type empty;
          description "Do not send interface state change traps";
        }
        leaf strict-bfd {
          type empty;
          description "Enable strict bfd over this interface";
        }
        container post-convergence-lfa {
          description "Protect interface using post-convergence backup path";
          presence "enable post-convergence-lfa";
          container node-protection {
            description "Compute backup path assuming node failure";
            presence "enable node-protection";
            leaf cost {
              type uint16 {
                range "1 .. 65535";
              }
              description "Cost for node protection";
            }
          }
          leaf srlg-protection {
            type empty;
            description "Compute backup path assuming SRLG failure";
          }
          leaf fate-sharing-protection {
            type empty;
            description "Compute backup path assuming fate-sharing group failure";
          }
        }
        leaf te-metric {
          type uint32 {
            range "1 .. 4294967295";
          }
          description "Traffic engineering metric";
        }
        container ldp-synchronization {
          description "Advertise maximum metric until LDP is operational";
          presence "enable ldp-synchronization";
          uses ldp-sync-obj;
        }
        container ipv4-adjacency-segment {
          description "Configure ipv4 adjacency segment";
          container protected {
            description "Adjacency SID is eligible for protection";
            choice adjsid-type {
              case case_1 {
                container index {
                  description "Adjacency SID indexed from SRGB";
                  leaf index-number {
                    type uint32 {
                      range "0 .. 199999";
                    }
                  }
                }
              }
              case case_2 {
                leaf label {
                  type uint32 {
                    range "16 .. 1048575";
                  }
                  description "Adjacency SID from static label pool";
                }
              }
              case case_3 {
                leaf dynamic {
                  type empty;
                  description "Dynamically allocate an adjacency segment";
                }
              }
            }
          }
          container unprotected {
            description "Adjacency SID uneligible for protection";
            choice adjsid-type {
              case case_1 {
                container index {
                  description "Adjacency SID indexed from SRGB";
                  leaf index-number {
                    type uint32 {
                      range "0 .. 199999";
                    }
                  }
                }
              }
              case case_2 {
                leaf label {
                  type uint32 {
                    range "16 .. 1048575";
                  }
                  description "Adjacency SID from static label pool";
                }
              }
              case case_3 {
                leaf dynamic {
                  type empty;
                  description "Dynamically allocate an adjacency segment";
                }
              }
            }
          }
        }
        list lan-neighbor {
          description "Configuration specific to a LAN neighbor";
          key name;
          ordered-by user;
          leaf name {
            type "jt:ipaddr";
            description "Address of neighbor";
          }
          container ipv4-adjacency-segment {
            description "Configure ipv4 adjacency segment";
            container protected {
              description "Adjacency SID is eligible for protection";
              choice adjsid-type {
                case case_1 {
                  container index {
                    description "Adjacency SID indexed from SRGB";
                    leaf index-number {
                      type uint32 {
                        range "0 .. 199999";
                      }
                    }
                  }
                }
                case case_2 {
                  leaf label {
                    type uint32 {
                      range "16 .. 1048575";
                    }
                    description "Adjacency SID from static label pool";
                  }
                }
                case case_3 {
                  leaf dynamic {
                    type empty;
                    description "Dynamically allocate an adjacency segment";
                  }
                }
              }
            }
            container unprotected {
              description "Adjacency SID uneligible for protection";
              choice adjsid-type {
                case case_1 {
                  container index {
                    description "Adjacency SID indexed from SRGB";
                    leaf index-number {
                      type uint32 {
                        range "0 .. 199999";
                      }
                    }
                  }
                }
                case case_2 {
                  leaf label {
                    type uint32 {
                      range "16 .. 1048575";
                    }
                    description "Adjacency SID from static label pool";
                  }
                }
                case case_3 {
                  leaf dynamic {
                    type empty;
                    description "Dynamically allocate an adjacency segment";
                  }
                }
              }
            }
          }
        }
        leaf delay-metric {
          type uint32 {
            range "0 .. 16777215";
          }
          description "Delay metric";
          units microseconds;
        }
        container delay-measurement {
          description "Enable delay measurement";
          presence "enable delay-measurement";
          leaf probe-interval {
            type uint32 {
              range "1 .. 255";
            }
            description "Probe interval";
            units seconds;
          }
          leaf probe-count {
            type uint32 {
              range "1 .. 15";
            }
            description "Probe count";
          }
          container advertisement {
            description "Delay advertisement";
            container periodic {
              description "Periodic advertisement parameters";
              leaf threshold {
                type uint32 {
                  range "0 .. 100";
                }
                description "Threshold";
                units percentage;
              }
              leaf interval {
                type uint32 {
                  range "30 .. 3600";
                }
                description "Interval";
                units seconds;
              }
            }
            container accelerated {
              description "Accelerated advertisement parameters";
              presence "enable accelerated";
              leaf threshold {
                type uint32 {
                  range "0 .. 100";
                }
                description "Threshold";
                units percentage;
              }
            }
          }
        }
        container application-specific {
          description "Advertise application-specific TE attributes";
          list attribute-group {
            description "Link attribute group name";
            key name;
            max-elements 1;
            ordered-by user;
            leaf name {
              type string;
              description "Link attribute group name";
            }
            leaf te-metric {
              type uint32 {
                range "1 .. 4294967295";
              }
              description "Traffic engineering metric for this attribute group";
            }
            leaf-list admin-group {
              type string;
              description "Administrative groups for this attribute-group";
              max-elements 16;
              ordered-by user;
            }
            leaf delay-metric {
              type uint32 {
                range "0 .. 16777215";
              }
              description "Delay metric for this attribute-group";
              units microseconds;
            }
            leaf advertise-interface-delay {
              type empty;
              description "Use interface specific static/dynamic delay values as applicable in ASLA Sub-TLVs";
            }
            container application {
              description "Standard Applications part of this attribute-group";
              leaf flex-algorithm {
                type empty;
                description "Set X flag in standard application bit mask";
              }
            }
          }
        }
      }
      leaf no-context-identifier-advertisement {
        type empty;
        description "Disable context identifier advertisments in this area";
      }
      list peer-interface {
        description "Configuration for peer interface";
        key name;
        ordered-by user;
        leaf name {
          type string;
          description "Name of peer interface";
        }
        choice enable-disable {
          case case_1 {
            leaf disable {
              type empty;
              description "Disable OSPF on this control peer";
            }
          }
        }
        leaf retransmit-interval {
          type uint32 {
            range "1 .. 65535";
          }
          description "Retransmission interval (seconds)";
        }
        leaf transit-delay {
          type uint32 {
            range "1 .. 65535";
          }
          description "Transit delay (seconds)";
        }
        leaf hello-interval {
          type uint32 {
            range "1 .. 255";
          }
          description "Hello interval (seconds)";
        }
        leaf dead-interval {
          type uint32 {
            range "1 .. 65535";
          }
          description "Dead interval (seconds)";
        }
        leaf mtu {
          type uint32 {
            range "128 .. 65535";
          }
          description "Maximum OSPF packet size";
        }
        choice auth {
          case case_1 {
            container authentication {
              uses juniper-ospf-authentication;
            }
          }
          case case_2 {
            container authentication-key {
              description "Authentication key";
              status deprecated;
              leaf keyname {
                type "jt:unreadable";
                description "Authentication key value";
              }
              leaf key-id {
                type uint32 {
                  range "0 .. 255";
                }
                description "Key ID for MD5 authentication";
              }
            }
          }
        }
        leaf demand-circuit {
          type empty;
          description "Interface functions as a demand circuit";
        }
        leaf flood-reduction {
          type empty;
          description "Enable flood reduction";
        }
        leaf no-neighbor-down-notification {
          type empty;
          description "Don't inform other protocols about neighbor down events";
        }
      }
      leaf no-source-packet-routing {
        type empty;
        description "Disable SPRING in this area";
      }
      list context-identifier {
        description "Configure context identifier in support of edge protection";
        key name;
        ordered-by user;
        leaf name {
          type "jt:ipv4addr";
          description "Context identifier";
        }
      }
      list label-switched-path {
        description "Configuration for advertisement of a label-switched path";
        key name;
        ordered-by user;
        leaf name {
          type string {
            length "1 .. 64";
          }
          description "Name of label-switched path to be advertised";
        }
        choice enable-disable {
          case case_1 {
            leaf disable {
              type empty;
              description "Disable OSPF on this label-switched path";
            }
          }
        }
        leaf metric {
          type uint16 {
            range "1 .. 65535";
          }
          description "Interface metric";
        }
        list topology {
          description "Topology specific attributes";
          key name;
          ordered-by user;
          leaf name {
            type string;
            description "Topology name";
          }
          leaf disable {
            type empty;
            description "Disable this topology";
          }
          leaf metric {
            type uint16 {
              range "1 .. 65535";
            }
            description "Topology metric";
          }
          container bandwidth-based-metrics {
            description "Configure bandwidth based metrics";
            list bandwidth {
              description "Bandwidth threshold";
              key name;
              leaf name {
                type string;
              }
              leaf metric {
                type uint16 {
                  range "1 .. 65535";
                }
                description "Metric associated with specified bandwidth";
              }
            }
          }
        }
      }
    }
    choice enable-disable {
      case case_1 {
        leaf disable {
          type empty;
          description "Disable OSPF";
        }
      }
    }
    container traceoptions {
      description "Trace options for OSPF";
      container file {
        description "Trace file options";
        leaf filename {
          type string {
            length "1 .. 1024";
          }
          description "Name of file in which to write trace information";
        }
        leaf replace {
          type empty;
          description "Replace trace file rather than appending to it";
          status deprecated;
        }
        leaf size {
          type string;
          description "Maximum trace file size";
        }
        leaf files {
          type uint32 {
            range "2 .. 1000";
          }
          default "10";
          description "Maximum number of trace files";
        }
        leaf no-stamp {
          type empty;
          description "Do not timestamp trace file";
          status deprecated;
        }
        choice world-readable-choice {
          leaf world-readable {
            type empty;
            description "Allow any user to read the log file";
          }
          leaf no-world-readable {
            type empty;
            description "Don't allow any user to read the log file";
          }
        }
      }
      list flag {
        description "Tracing parameters";
        key name;
        ordered-by user;
        leaf name {
          type enumeration {
            enum spf {
              description "Trace SPF calculations";
            }
            enum error {
              description "Trace errored packets";
            }
            enum event {
              description "Trace OSPF state machine events";
            }
            enum packet-dump {
              description "Dump the contents of selected packet types";
            }
            enum flooding {
              description "Trace LSA flooding";
            }
            enum lsa-analysis {
              description "Trace LSA analysis";
            }
            enum packets {
              description "Trace all OSPF packets";
            }
            enum hello {
              description "Trace hello packets";
            }
            enum database-description {
              description "Trace database description packets";
            }
            enum lsa-request {
              description "Trace LSA request packets";
            }
            enum lsa-update {
              description "Trace LSA update packets";
            }
            enum lsa-ack {
              description "Trace LSA acknowledgment packets";
            }
            enum ldp-synchronization {
              description "Trace synchronization between OSPF and LDP";
            }
            enum on-demand {
              description "Trace demand circuit extensions";
            }
            enum nsr-synchronization {
              description "Trace NSR synchronization events";
            }
            enum graceful-restart {
              description "Trace graceful restart";
            }
            enum restart-signaling {
              description "Trace restart signaling";
            }
            enum traffic-statistics {
              description "Trace Segment Routing Traffic Statistics";
            }
            enum backup-spf {
              description "Trace backup SPF (LFA) specific events";
            }
            enum source-packet-routing {
              description "Trace source packet routing (SPRING) events";
            }
            enum post-convergence-lfa {
              description "Trace post-convergence-lfa related events";
            }
            enum flex-algorithm {
              description "Trace flex-algorithm related events";
            }
            enum rmopd {
              description "Trace rmopd interactions";
            }
            enum route {
              description "Trace routing information";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
        leaf send {
          type empty;
          description "Trace transmitted packets";
        }
        leaf receive {
          type empty;
          description "Trace received packets";
        }
        leaf detail {
          type empty;
          description "Trace detailed information";
        }
        leaf disable {
          type empty;
          description "Disable this trace flag";
        }
      }
    }
    leaf prefix-export-limit {
      type uint32 {
        range "0 .. 4294967295";
      }
      description "Maximum number of prefixes that can be exported";
    }
    container rib-groups {
      description "Routing table groups for importing OSPF routes";
      leaf inet {
        type string;
        description "Name of the IPv4/v6 routing table group";
      }
      leaf inet3 {
        type string;
        description "Name of the IPv4/v6 inet.3 routing table group";
      }
    }
    leaf job-stats {
      type empty;
      description "Collect job statistics";
    }
    container overload {
      description "Set the overload mode (repel transit traffic)";
      presence "enable overload";
      leaf timeout {
        type uint32 {
          range "60 .. 3600";
        }
        description "Time after which overload mode is reset";
        units seconds;
      }
      leaf allow-route-leaking {
        type empty;
        description "Allow routes to be leaked when overload is configured";
      }
      leaf stub-network {
        type empty;
        description "Advertise Stub Network with maximum metric";
      }
      leaf intra-area-prefix {
        type empty;
        description "Advertise Intra Area Prefix with maximum metric";
      }
      leaf as-external {
        type empty;
        description "Advertise As External with maximum usable metric";
      }
    }
    container database-protection {
      description "Configure database protection attributes";
      presence "enable database-protection";
      leaf maximum-lsa {
        type uint32 {
          range "1 .. 1000000";
        }
        description "Maximum allowed non self-generated LSAs";
      }
      leaf warning-only {
        type empty;
        description "Emit only a warning when LSA maximum limit is exceeded";
      }
      leaf warning-threshold {
        type uint8 {
          range "30 .. 100";
        }
        description "Percentage of LSA maximum above which to trigger warning";
        units percent;
      }
      leaf ignore-count {
        type uint8 {
          range "1 .. 32";
        }
        description "Maximum number of times to go into ignore state";
      }
      leaf ignore-time {
        type uint16 {
          range "30 .. 3600";
        }
        description "Time to stay in ignore state and ignore all neighbors";
        units seconds;
      }
      leaf reset-time {
        type uint32 {
          range "60 .. 86400";
        }
        description "Time after which the ignore count gets reset to zero";
        units seconds;
      }
    }
    container graceful-restart {
      description "Configure graceful restart attributes";
      choice enable-disable {
        case case_1 {
          leaf disable {
            type empty;
            description "Disable OSPF graceful restart capability";
          }
        }
      }
      leaf restart-duration {
        type uint32 {
          range "1 .. 3600";
        }
        description "Time for all neighbors to become full";
        units seconds;
      }
      leaf notify-duration {
        type uint32 {
          range "1 .. 3600";
        }
        description "Time to send all max-aged grace LSAs";
        units seconds;
      }
      container helper-disable {
        description "Disable graceful restart helper capability";
        presence "enable helper-disable";
        choice disable-choices {
          case case_1 {
            leaf standard {
              type empty;
              description "Disable helper-mode for rfc3623 based GR";
            }
          }
          case case_2 {
            leaf restart-signaling {
              type empty;
              description "Disable helper mode for restart-signaling ";
            }
          }
          case case_3 {
            leaf both {
              type empty;
              description "Disable helper mode for both the types of GR";
            }
          }
        }
      }
      leaf no-strict-lsa-checking {
        type empty;
        description "Do not abort graceful helper mode upon LSA changes";
      }
    }
    leaf route-type-community {
      type enumeration {
        enum iana {
          description "BGP extended community value used is 0x0306";
        }
        enum vendor {
          description "Vendor BGP extended community value used is 0x8000";
        }
      }
      description "Specify BGP extended community value to encode OSPF route type";
    }
    container domain-id {
      description "Configure domain ID";
      choice domain_id_or_disable {
        case case_1 {
          leaf domain-id {
            type string;
            description "Domain ID";
          }
        }
        case case_2 {
          leaf disable {
            type empty;
            description "Disable domain ID";
          }
        }
      }
    }
    choice domain_vpn_tag_or_disable {
      case case_1 {
        leaf domain-vpn-tag {
          type uint32 {
            range "0 .. 4294967295";
          }
          description "Domain VPN tag for external LSA";
        }
      }
      case case_2 {
        leaf no-domain-vpn-tag {
          type empty;
          description "Disable domain VPN tag";
        }
      }
    }
    leaf preference {
      type uint32;
      description "Preference of internal routes";
    }
    leaf external-preference {
      type uint32;
      description "Preference of external routes";
    }
    leaf labeled-preference {
      type uint32;
      description "Preference of labeled routes";
    }
    leaf-list export {
      type "jt:policy-algebra";
      description "Export policy";
      ordered-by user;
    }
    leaf-list import {
      type "jt:policy-algebra";
      description "Import policy (for external routes or setting priority)";
      ordered-by user;
    }
    leaf reference-bandwidth {
      type string;
      description "Bandwidth for calculating metric defaults";
    }
    leaf lsa-refresh-interval {
      type uint32 {
        range "25 .. 50";
      }
      default "50";
      description "LSA refresh interval (minutes)";
    }
    leaf spf-delay {
      type uint32 {
        range "50 .. 8000";
      }
      description "Time to wait before running an SPF";
      status deprecated;
      units milliseconds;
    }
    leaf no-rfc-1583 {
      type empty;
      description "Disable RFC1583 compatibility";
    }
    leaf forwarding-address-to-broadcast {
      type empty;
      description "Set forwarding address in Type 5 LSA in broadcast network";
    }
    choice nssa-abr-option {
      case case_1 {
        leaf no-nssa-abr {
          type empty;
          description "Disable full NSSA functionality at ABR";
        }
      }
    }
    container sham-link {
      description "Configure parameters for sham links";
      presence "enable sham-link";
      leaf local {
        type "jt:ipaddr";
        description "Local sham link endpoint address";
      }
      leaf no-advertise-local {
        type empty;
        description "Don't advertise local sham link endpoint as stub in router LSA";
        status deprecated;
      }
    }
  }
  grouping juniper-ospf-authentication {
    description "Authentication information";
    choice authentication-type {
      case case_1 {
        leaf simple-password {
          type "jt:unreadable";
          description "Authentication key";
        }
      }
      case case_2 {
        list md5 {
          description "MD5 authentication key";
          key name;
          ordered-by user;
          leaf name {
            type uint32 {
              range "0 .. 255";
            }
            description "Key ID for MD5 authentication";
          }
          leaf key {
            type "jt:unreadable";
            description "MD5 authentication key value";
          }
          leaf start-time {
            type "jt:time";
            description "Start time for key transmission (YYYY-MM-DD.HH:MM)";
          }
        }
      }
      case case_3 {
        list multi-active-md5 {
          description "Authentication Multiple active MD5 keys";
          key name;
          ordered-by user;
          leaf name {
            type uint32 {
              range "0 .. 255";
            }
            description "Key ID for MD5 authentication";
          }
          leaf key {
            type "jt:unreadable";
            description "MD5 authentication key value";
          }
          leaf delete-if-not-inuse {
            type empty;
            description "Delete this key if not in use";
          }
        }
      }
      case case_4 {
        leaf keychain {
          type string {
            length "1 .. 128";
          }
          description "Key chain name";
        }
      }
    }
  }
  grouping juniper-protocols-ospf3 {
    list realm {
      description "OSPFv3 realm configuration";
      key name;
      ordered-by user;
      leaf name {
        type enumeration {
          enum ipv6-unicast {
            description "IPv6 unicast realm";
          }
          enum ipv6-multicast {
            description "IPv6 multicast realm";
          }
          enum ipv4-unicast {
            description "IPv4 unicast realm";
          }
          enum ipv4-multicast {
            description "IPv4 multicast realm";
          }
        }
        description "OSPFv3 realm name";
      }
      list topology {
        description "Topology parameters";
        key name;
        ordered-by user;
        leaf name {
          type string;
          description "Topology name";
        }
        leaf disable {
          type empty;
          description "Disable this topology";
        }
        leaf topology-id {
          type uint8 {
            range "32 .. 127";
          }
          description "Topology identifier";
        }
        leaf overload {
          type empty;
          description "Set the overload mode (repel transit traffic)";
        }
        leaf rib-group {
          type string;
          description "Routing table group for importing routes";
        }
        container spf-options {
          description "Configure options for SPF";
          container microloop-avoidance {
            description "Configure microloop avoidance mechanism";
            container post-convergence-path {
              description "Temporarily install post-convergence path for routes potentially affected by microloops";
              presence "enable post-convergence-path";
              leaf delay {
                type uint32 {
                  range "500 .. 60000";
                }
                description "Time after which temporary post-convergence paths are removed";
                units milliseconds;
              }
              leaf maximum-labels {
                type uint32 {
                  range "2 .. 8";
                }
                description "Maximum number of labels installed for post-convergence paths";
              }
            }
          }
          leaf delay {
            type uint32 {
              range "50 .. 8000";
            }
            description "Time to wait before running an SPF";
            units milliseconds;
          }
          leaf holddown {
            type uint32 {
              range "2000 .. 20000";
            }
            description "Time to hold down before running an SPF";
            units milliseconds;
          }
          leaf rapid-runs {
            type uint32 {
              range "1 .. 10";
            }
            description "Number of maximum rapid SPF runs before holddown";
          }
          leaf no-ignore-our-externals {
            type empty;
            description "Do not ignore self-generated external and NSSA LSAs";
          }
        }
        container backup-spf-options {
          description "Configure options for backup SPF";
          container remote-backup-calculation {
            description "Calculate Remote LFA backup nexthops";
            presence "enable remote-backup-calculation";
            container pq-nodes-nearest-to-source {
              description "PQ nodes selection based upon nearest to source";
              leaf percent {
                type uint32 {
                  range "10 .. 100";
                }
                description "Selection percentage for nearest to source";
              }
            }
          }
          container use-post-convergence-lfa {
            description "Calculate post-convergence backup paths";
            presence "enable use-post-convergence-lfa";
            leaf maximum-labels {
              type uint32 {
                range "2 .. 8";
              }
              description "Maximum number of labels installed for post-convergence paths";
            }
            leaf maximum-backup-paths {
              type uint32 {
                range "1 .. 8";
              }
              description "Maximum number of equal-cost post-convergence paths installed";
            }
          }
          leaf use-source-packet-routing {
            type empty;
            description "Use spring backup paths for inet.0 routes";
          }
          leaf disable {
            type empty;
            description "Do not run backup SPF";
          }
          leaf no-install {
            type empty;
            description "Do not install backup nexthops into the RIB";
          }
          leaf downstream-paths-only {
            type empty;
            description "Use only downstream backup paths";
          }
          container per-prefix-calculation {
            description "Calculate backup nexthops for non-best prefix originators";
            leaf stubs {
              type empty;
              description "Per prefix calculation for stubs only";
            }
            leaf summary {
              type empty;
              description "Per prefix calculation for summary originators only";
            }
            leaf externals {
              type empty;
              description "Per prefix calculation for externals";
            }
            leaf all {
              type empty;
              description "Per prefix calculation for all";
            }
          }
          leaf node-link-degradation {
            type empty;
            description "Degrade to link protection when nodelink protection not available";
          }
        }
        leaf prefix-export-limit {
          type uint32 {
            range "0 .. 4294967295";
          }
          description "Maximum number of prefixes that can be exported";
        }
      }
      container spf-options {
        description "Configure options for SPF";
        container microloop-avoidance {
          description "Configure microloop avoidance mechanism";
          container post-convergence-path {
            description "Temporarily install post-convergence path for routes potentially affected by microloops";
            presence "enable post-convergence-path";
            leaf delay {
              type uint32 {
                range "500 .. 60000";
              }
              description "Time after which temporary post-convergence paths are removed";
              units milliseconds;
            }
            leaf maximum-labels {
              type uint32 {
                range "2 .. 8";
              }
              description "Maximum number of labels installed for post-convergence paths";
            }
          }
        }
        leaf delay {
          type uint32 {
            range "50 .. 8000";
          }
          description "Time to wait before running an SPF";
          units milliseconds;
        }
        leaf holddown {
          type uint32 {
            range "2000 .. 20000";
          }
          description "Time to hold down before running an SPF";
          units milliseconds;
        }
        leaf rapid-runs {
          type uint32 {
            range "1 .. 10";
          }
          description "Number of maximum rapid SPF runs before holddown";
        }
        leaf no-ignore-our-externals {
          type empty;
          description "Do not ignore self-generated external and NSSA LSAs";
        }
      }
      container backup-spf-options {
        description "Configure options for backup SPF";
        container remote-backup-calculation {
          description "Calculate Remote LFA backup nexthops";
          presence "enable remote-backup-calculation";
          container pq-nodes-nearest-to-source {
            description "PQ nodes selection based upon nearest to source";
            leaf percent {
              type uint32 {
                range "10 .. 100";
              }
              description "Selection percentage for nearest to source";
            }
          }
        }
        container use-post-convergence-lfa {
          description "Calculate post-convergence backup paths";
          presence "enable use-post-convergence-lfa";
          leaf maximum-labels {
            type uint32 {
              range "2 .. 8";
            }
            description "Maximum number of labels installed for post-convergence paths";
          }
          leaf maximum-backup-paths {
            type uint32 {
              range "1 .. 8";
            }
            description "Maximum number of equal-cost post-convergence paths installed";
          }
        }
        leaf use-source-packet-routing {
          type empty;
          description "Use spring backup paths for inet.0 routes";
        }
        leaf disable {
          type empty;
          description "Do not run backup SPF";
        }
        leaf no-install {
          type empty;
          description "Do not install backup nexthops into the RIB";
        }
        leaf downstream-paths-only {
          type empty;
          description "Use only downstream backup paths";
        }
        container per-prefix-calculation {
          description "Calculate backup nexthops for non-best prefix originators";
          leaf stubs {
            type empty;
            description "Per prefix calculation for stubs only";
          }
          leaf summary {
            type empty;
            description "Per prefix calculation for summary originators only";
          }
          leaf externals {
            type empty;
            description "Per prefix calculation for externals";
          }
          leaf all {
            type empty;
            description "Per prefix calculation for all";
          }
        }
        leaf node-link-degradation {
          type empty;
          description "Degrade to link protection when nodelink protection not available";
        }
      }
      container traffic-engineering {
        description "Configure traffic engineering attributes";
        presence "enable traffic-engineering";
        leaf no-topology {
          type empty;
          description "Disable dissemination of TE link-state topology information";
        }
        leaf multicast-rpf-routes {
          type empty;
          description "Install routes for multicast RPF checks into inet.2";
        }
        leaf l3-unicast-topology {
          type empty;
          description "Download IGP topology into TED";
        }
        container ignore-lsp-metrics {
          description "Ignore label-switched path metrics when doing shortcuts";
          presence "enable ignore-lsp-metrics";
          leaf unconfigured-only {
            type empty;
            description "Ignore lsp metrics for unconfigured only";
          }
        }
        container shortcuts {
          description "Use label-switched paths as next hops, if possible";
          presence "enable shortcuts";
          leaf ignore-lsp-metrics {
            type empty;
            description "Ignore label-switched path metrics when doing shortcuts";
            status deprecated;
          }
          leaf lsp-metric-into-summary {
            type empty;
            description "Advertise LSP metric into summary LSAs";
          }
          list family {
            description "Address family specific traffic-engineering attributes";
            key name;
            ordered-by user;
            leaf name {
              type enumeration {
                enum inet {
                  description "IPv4 family";
                }
                enum inet-mpls {
                  description "IPv4-MPLS family";
                }
              }
            }
          }
        }
        leaf advertise-unnumbered-interfaces {
          type empty;
          description "Advertise unnumbered interfaces";
        }
        leaf credibility-protocol-preference {
          type empty;
          description "TED protocol credibility follows protocol preference";
        }
        container advertisement {
          description "Advertise TE parameters even if RSVP is not turned on";
          leaf always {
            type empty;
            description "Advertise TE parameters in TE LSAs";
          }
        }
        container tunnel-source-protocol {
          description "Protocols from which to pick label-switched paths";
          container rsvp {
            description "Pick label-switched paths from rsvp";
            presence "enable rsvp";
            leaf preference {
              type uint32 {
                range "1 .. 255";
              }
              description "Preference for label-switched paths from this protocol";
            }
          }
          container spring-te {
            description "Pick label-switched paths from spring-te";
            presence "enable spring-te";
            leaf preference {
              type uint32 {
                range "1 .. 255";
              }
              description "Preference for label-switched paths from this protocol";
            }
          }
        }
      }
      container source-packet-routing {
        description "Enable source packet routing (SPRING)";
        presence "enable source-packet-routing";
        container adjacency-segment {
          description "Attributes for adjacency segments in spring";
          leaf hold-time {
            type uint32 {
              range "180000 .. 900000";
            }
            description "Retain time of Adjacency segment after isolating from an interface";
          }
        }
        leaf-list prefix-segment {
          type "jt:policy-algebra";
          description "Prefix Segment policy";
          ordered-by user;
        }
        leaf explicit-null {
          type empty;
          description "Set E and P bits in all Prefix SID advertisements";
        }
        container node-segment {
          description "Enable support for Node segments in SPRING";
          presence "enable node-segment";
          leaf ipv4-index {
            type uint32 {
              range "0 .. 199999";
            }
            description "Set ipv4 node segment index";
          }
          leaf index-range {
            type uint32 {
              range "32 .. 16385";
            }
            description "Set range of node segment indices allowed";
          }
        }
        container srgb {
          description "Set the SRGB global block in SPRING";
          leaf start-label {
            type uint32;
            description "Start range for SRGB label block";
          }
          leaf index-range {
            type uint32;
            description "Index to the SRGB start label block";
          }
        }
        leaf mapping-server {
          type string;
          description "Mapping server name";
        }
        leaf install-prefix-sid-for-best-route {
          type empty;
          description "For best route install a exact prefix sid route";
        }
        leaf ldp-stitching {
          type empty;
          description "Enable SR to LDP stitching";
        }
        leaf-list flex-algorithm {
          type uint32 {
            range "128 .. 255";
          }
          description "Flex-algorithms we would like to participate in";
          max-elements 16;
        }
        leaf strict-asla-based-flex-algorithm {
          type empty;
          description "Flex-Algorithm to ignore links not having ASLA sub-TLVs";
        }
        container sensor-based-stats {
          description "Configure sensor based stats in SPRING";
          container per-interface-per-member-link {
            description "Configure sensor based stats per nexthop";
            leaf ingress {
              type empty;
              description "Enable sensor based stats on ingress interface";
            }
            leaf egress {
              type empty;
              description "Enable sensor based stats on egress interface";
            }
          }
          container per-sid {
            description "Configure sensor based stats per spring route";
            leaf ingress {
              type empty;
              description "Enable sensor based stats for per-sid ingress accounting";
            }
            leaf egress {
              type empty;
              description "Enable sensor based stats for IP-MPLS egress accounting";
            }
          }
        }
      }
      list area {
        description "Configure an OSPF area";
        key name;
        ordered-by user;
        leaf name {
          type "jt:areaid";
          description "Area ID";
        }
        choice stub-option {
          case case_1 {
            container stub {
              description "Configure a stub area";
              presence "enable stub";
              leaf default-metric {
                type uint32 {
                  range "1 .. 16777215";
                }
                description "Metric for the default route in this stub area";
              }
              choice summaries-choice {
                leaf summaries {
                  type empty;
                  description "Flood summary LSAs into this stub area";
                }
                leaf no-summaries {
                  type empty;
                  description "Don't flood summary LSAs into this stub area";
                }
              }
            }
          }
          case case_2 {
            container nssa {
              description "Configure a not-so-stubby area";
              presence "enable nssa";
              container default-lsa {
                description "Configure a default LSA";
                presence "enable default-lsa";
                leaf default-metric {
                  type uint32 {
                    range "1 .. 16777215";
                  }
                  description "Metric for the default route in this area";
                }
                leaf metric-type {
                  type uint32 {
                    range "1 .. 2";
                  }
                  description "External metric type for the default type 7 LSA";
                }
                leaf type-7 {
                  type empty;
                  description "Flood type 7 default LSA if no-summaries is configured";
                }
              }
              leaf default-metric {
                type uint32 {
                  range "1 .. 16777215";
                }
                description "Metric for the default route in this area";
                status deprecated;
              }
              leaf metric-type {
                type uint32 {
                  range "1 .. 2";
                }
                description "External metric type for the default type 7 LSA";
                status deprecated;
              }
              choice summaries-choice {
                leaf summaries {
                  type empty;
                  description "Flood summary LSAs into this NSSA area";
                }
                leaf no-summaries {
                  type empty;
                  description "Don't flood summary LSAs into this NSSA area";
                }
              }
              list area-range {
                description "Configure NSSA area ranges";
                key name;
                ordered-by user;
                leaf name {
                  type "jt:ipprefix";
                  description "Range to summarize NSSA routes in this area";
                }
                leaf restrict {
                  type empty;
                  description "Restrict advertisement of this area range";
                }
                leaf exact {
                  type empty;
                  description "Enforce exact match for advertisement of this area range";
                }
                container override-metric {
                  description "Override the dynamic metric for this area-range";
                  presence "enable override-metric";
                  leaf metric {
                    type uint32 {
                      range "1 .. 16777215";
                    }
                    description "Metric value";
                  }
                  leaf metric-type {
                    type uint32 {
                      range "1 .. 2";
                    }
                    default "1";
                    description "Set the metric type for the override metric";
                  }
                }
              }
            }
          }
        }
        list area-range {
          description "Configure area ranges";
          key name;
          ordered-by user;
          leaf name {
            type "jt:ipprefix";
            description "Range to summarize routes in this area";
          }
          leaf restrict {
            type empty;
            description "Restrict advertisement of this area range";
          }
          leaf exact {
            type empty;
            description "Enforce exact match for advertisement of this area range";
          }
          leaf override-metric {
            type uint32 {
              range "1 .. 16777215";
            }
            description "Override the dynamic metric for this area-range";
          }
        }
        leaf-list network-summary-export {
          type "jt:policy-algebra";
          description "Export policy for Type 3 Summary LSAs";
          ordered-by user;
        }
        leaf-list network-summary-import {
          type "jt:policy-algebra";
          description "Import policy for Type 3 Summary LSAs";
          ordered-by user;
        }
        leaf-list inter-area-prefix-export {
          type "jt:policy-algebra";
          description "Export policy for Inter Area Prefix LSAs";
          ordered-by user;
        }
        leaf-list inter-area-prefix-import {
          type "jt:policy-algebra";
          description "Import policy for Inter Area Prefix LSAs";
          ordered-by user;
        }
        leaf authentication-type {
          type enumeration {
            enum none {
              description "No authentication";
              status deprecated;
            }
            enum simple {
              description "Simple password authentication";
              status deprecated;
            }
            enum md5 {
              description "MD5 authentication";
              status deprecated;
            }
          }
          description "Authentication type";
          status deprecated;
        }
        list virtual-link {
          description "Configure virtual links";
          key "neighbor-id transit-area";
          ordered-by user;
          leaf neighbor-id {
            type "jt:ipv4addr";
            description "Router ID of a virtual neighbor";
          }
          leaf transit-area {
            type "jt:areaid";
            description "Transit area in common with virtual neighbor";
          }
          choice enable-disable {
            case case_1 {
              leaf disable {
                type empty;
                description "Disable this virtual link";
              }
            }
          }
          leaf retransmit-interval {
            type uint32 {
              range "1 .. 65535";
            }
            description "Retransmission interval (seconds)";
          }
          leaf transit-delay {
            type uint32 {
              range "1 .. 65535";
            }
            description "Transit delay (seconds)";
          }
          leaf hello-interval {
            type uint32 {
              range "1 .. 255";
            }
            description "Hello interval (seconds)";
          }
          leaf dead-interval {
            type uint32 {
              range "1 .. 65535";
            }
            description "Dead interval (seconds)";
          }
          leaf mtu {
            type uint32 {
              range "128 .. 65535";
            }
            description "Maximum OSPF packet size";
          }
          choice auth {
            case case_1 {
              container authentication {
                uses juniper-ospf-authentication;
              }
            }
            case case_2 {
              container authentication-key {
                description "Authentication key";
                status deprecated;
                leaf keyname {
                  type "jt:unreadable";
                  description "Authentication key value";
                }
                leaf key-id {
                  type uint32 {
                    range "0 .. 255";
                  }
                  description "Key ID for MD5 authentication";
                }
              }
            }
          }
          leaf demand-circuit {
            type empty;
            description "Interface functions as a demand circuit";
          }
          leaf flood-reduction {
            type empty;
            description "Enable flood reduction";
          }
          leaf no-neighbor-down-notification {
            type empty;
            description "Don't inform other protocols about neighbor down events";
          }
          leaf ipsec-sa {
            type string {
              length "1 .. 32";
            }
            description "IPSec security association name";
          }
          list topology {
            description "Topology specific attributes";
            key name;
            ordered-by user;
            leaf name {
              type string;
              description "Topology name";
            }
            leaf disable {
              type empty;
              description "Disable this topology";
            }
            leaf metric {
              type uint16 {
                range "1 .. 65535";
              }
              description "Topology metric";
            }
            container bandwidth-based-metrics {
              description "Configure bandwidth based metrics";
              list bandwidth {
                description "Bandwidth threshold";
                key name;
                leaf name {
                  type string;
                }
                leaf metric {
                  type uint16 {
                    range "1 .. 65535";
                  }
                  description "Metric associated with specified bandwidth";
                }
              }
            }
          }
        }
        list sham-link-remote {
          description "Configure parameters for remote sham link endpoint";
          key name;
          ordered-by user;
          leaf name {
            type "jt:ipaddr";
            description "Remote sham link endpoint address";
          }
          leaf metric {
            type uint16 {
              range "1 .. 65535";
            }
            description "Sham link metric";
          }
          leaf ipsec-sa {
            type string {
              length "1 .. 32";
            }
            description "IPSec security association name";
          }
          leaf demand-circuit {
            type empty;
            description "Interface functions as a demand circuit";
          }
          leaf flood-reduction {
            type empty;
            description "Enable flood reduction";
          }
          list topology {
            description "Topology specific attributes";
            key name;
            ordered-by user;
            leaf name {
              type string;
              description "Topology name";
            }
            leaf disable {
              type empty;
              description "Disable this topology";
            }
            leaf metric {
              type uint16 {
                range "1 .. 65535";
              }
              description "Topology metric";
            }
            container bandwidth-based-metrics {
              description "Configure bandwidth based metrics";
              list bandwidth {
                description "Bandwidth threshold";
                key name;
                leaf name {
                  type string;
                }
                leaf metric {
                  type uint16 {
                    range "1 .. 65535";
                  }
                  description "Metric associated with specified bandwidth";
                }
              }
            }
          }
        }
        list interface {
          description "Include an interface in this area";
          key name;
          ordered-by user;
          leaf name {
            type "jt:ipv4addr-or-interface";
            description "Interface name";
          }
          choice enable-disable {
            case case_1 {
              leaf disable {
                type empty;
                description "Disable OSPF on this interface";
              }
            }
          }
          leaf interface-type {
            type enumeration {
              enum nbma {
                description "Nonbroadcast multiaccess";
              }
              enum p2mp {
                description "Point-to-multipoint NBMA";
              }
              enum p2p {
                description "Point-to-point";
              }
              enum p2mp-over-lan {
                description "Point-to-multipoint over LAN mode";
              }
            }
            description "Type of interface";
          }
          choice protection-type {
            case case_1 {
              leaf link-protection {
                type empty;
                description "Protect interface from link faults only";
              }
            }
            case case_2 {
              leaf node-link-protection {
                type empty;
                description "Protect interface from both link and node faults";
              }
            }
          }
          leaf no-eligible-backup {
            type empty;
            description "Not eligible to backup traffic from protected interfaces";
          }
          leaf no-eligible-remote-backup {
            type empty;
            description "Not eligible for Remote-LFA backup traffic from protected interfaces";
          }
          container passive {
            description "Do not run OSPF, but advertise it";
            presence "enable passive";
            container traffic-engineering {
              description "Advertise TE link information";
              leaf remote-node-id {
                type "jt:ipaddr";
                description "Remote address of the link";
              }
              leaf remote-node-router-id {
                type "jt:ipv4addr";
                description "TE Router-ID of the remote node";
              }
            }
          }
          leaf secondary {
            type empty;
            description "Treat interface as secondary";
          }
          leaf own-router-lsa {
            type empty;
            description "Generate a separate router LSA for this interface";
          }
          container bandwidth-based-metrics {
            description "Configure bandwidth based metrics";
            list bandwidth {
              description "Bandwidth threshold";
              key name;
              leaf name {
                type string;
              }
              leaf metric {
                type uint16 {
                  range "1 .. 65535";
                }
                description "Metric associated with specified bandwidth";
              }
            }
          }
          leaf metric {
            type uint16 {
              range "1 .. 65535";
            }
            description "Interface metric";
          }
          leaf priority {
            type uint32 {
              range "0 .. 255";
            }
            description "Designated router priority";
          }
          leaf retransmit-interval {
            type uint32 {
              range "1 .. 65535";
            }
            description "Retransmission interval (seconds)";
          }
          leaf transit-delay {
            type uint32 {
              range "1 .. 65535";
            }
            description "Transit delay (seconds)";
          }
          leaf hello-interval {
            type uint32 {
              range "1 .. 255";
            }
            description "Hello interval (seconds)";
          }
          leaf dead-interval {
            type uint32 {
              range "1 .. 65535";
            }
            description "Dead interval (seconds)";
          }
          leaf mtu {
            type uint32 {
              range "128 .. 65535";
            }
            description "Maximum OSPF packet size";
          }
          choice auth {
            case case_1 {
              container authentication {
                uses juniper-ospf-authentication;
              }
            }
            case case_2 {
              container authentication-key {
                description "Authentication key";
                status deprecated;
                leaf keyname {
                  type "jt:unreadable";
                  description "Authentication key value";
                }
                leaf key-id {
                  type uint32 {
                    range "0 .. 255";
                  }
                  description "Key ID for MD5 authentication";
                }
              }
            }
          }
          leaf demand-circuit {
            type empty;
            description "Interface functions as a demand circuit";
          }
          leaf flood-reduction {
            type empty;
            description "Enable flood reduction";
          }
          leaf no-neighbor-down-notification {
            type empty;
            description "Don't inform other protocols about neighbor down events";
          }
          leaf ipsec-sa {
            type string {
              length "1 .. 32";
            }
            description "IPSec security association name";
          }
          list topology {
            description "Topology specific attributes";
            key name;
            ordered-by user;
            leaf name {
              type string;
              description "Topology name";
            }
            leaf disable {
              type empty;
              description "Disable this topology";
            }
            leaf metric {
              type uint16 {
                range "1 .. 65535";
              }
              description "Topology metric";
            }
            container bandwidth-based-metrics {
              description "Configure bandwidth based metrics";
              list bandwidth {
                description "Bandwidth threshold";
                key name;
                leaf name {
                  type string;
                }
                leaf metric {
                  type uint16 {
                    range "1 .. 65535";
                  }
                  description "Metric associated with specified bandwidth";
                }
              }
            }
          }
          leaf transmit-interval {
            type uint32 {
              range "1 .. 4294967295";
            }
            description "OSPF packet transmit interval (milliseconds)";
            status deprecated;
          }
          container bfd-liveness-detection {
            description "Bidirectional Forwarding Detection options";
            leaf version {
              type enumeration {
                enum 0 {
                  description "BFD version 0 (deprecated)";
                }
                enum 1 {
                  description "BFD version 1";
                }
                enum automatic {
                  description "Choose BFD version automatically";
                }
              }
              default "automatic";
              description "BFD protocol version number";
            }
            leaf minimum-interval {
              type uint32 {
                range "1 .. 255000";
              }
              description "Minimum transmit and receive interval";
              units milliseconds;
            }
            leaf minimum-transmit-interval {
              type uint32 {
                range "1 .. 255000";
              }
              description "Minimum transmit interval";
              status deprecated;
              units milliseconds;
            }
            leaf minimum-receive-interval {
              type uint32 {
                range "1 .. 255000";
              }
              description "Minimum receive interval";
              units milliseconds;
            }
            leaf multiplier {
              type uint32 {
                range "1 .. 255";
              }
              default "3";
              description "Detection time multiplier";
            }
            leaf inline-disable {
              type empty;
              description "Disable inline mode for this BFD session";
            }
            leaf pdu-size {
              type uint32 {
                range "24 .. 9000";
              }
              default "24";
              description "BFD transport protocol payload size";
            }
            choice adaptation-choice {
              case case_1 {
                leaf no-adaptation {
                  type empty;
                  description "Disable adaptation";
                }
              }
            }
            container transmit-interval {
              description "Transmit-interval options";
              leaf minimum-interval {
                type uint32 {
                  range "1 .. 255000";
                }
                description "Minimum transmit interval";
                units milliseconds;
              }
              leaf threshold {
                type uint32;
                description "High transmit interval triggering a trap";
                units milliseconds;
              }
            }
            container detection-time {
              description "Detection-time options";
              leaf threshold {
                type uint32;
                description "High detection-time triggering a trap";
                units milliseconds;
              }
            }
            container authentication {
              description "Authentication options";
              leaf key-chain {
                type string;
                description "Key chain name";
              }
              leaf algorithm {
                type enumeration {
                  enum simple-password {
                    description "Simple password";
                  }
                  enum keyed-md5 {
                    description "Keyed message Digest 5";
                  }
                  enum meticulous-keyed-md5 {
                    description "Meticulous keyed message Digest 5";
                  }
                  enum keyed-sha-1 {
                    description "Keyed secure hash algorithm (SHA1) ";
                  }
                  enum meticulous-keyed-sha-1 {
                    description "Meticulous keyed secure hash algorithm (SHA1) ";
                  }
                }
                description "Algorithm name";
              }
              leaf loose-check {
                type empty;
                description "Verify authentication only if authentication is negotiated";
              }
            }
            container echo {
              description "Echo mode parameters";
              leaf minimum-interval {
                type uint32 {
                  range "100 .. 255000";
                }
                description "Minimum transmit and receive interval";
                units milliseconds;
              }
            }
            container echo-lite {
              description "Echo-lite more parameters";
              leaf minimum-interval {
                type uint32 {
                  range "100 .. 255000";
                }
                description "Minimum transmit and receive interval";
                units milliseconds;
              }
            }
            leaf full-neighbors-only {
              type empty;
              description "Setup BFD sessions only to Full neighbors";
            }
            leaf holddown-interval {
              type uint32 {
                range "0 .. 255000";
              }
              description "Time to hold the session-UP notification to the client";
              units milliseconds;
            }
          }
          leaf dynamic-neighbors {
            type empty;
            description "Learn neighbors dynamically on a p2mp interface";
          }
          leaf no-advertise-adjacency-segment {
            type empty;
            description "Do not advertise an adjacency segment for this interface";
          }
          list neighbor {
            description "NBMA neighbor";
            key name;
            ordered-by user;
            leaf name {
              type "jt:ipaddr";
              description "Address of neighbor";
            }
            leaf eligible {
              type empty;
              description "Eligible to be DR on an NBMA network";
            }
          }
          leaf poll-interval {
            type uint32 {
              range "1 .. 65535";
            }
            description "Poll interval for NBMA interfaces";
          }
          leaf no-interface-state-traps {
            type empty;
            description "Do not send interface state change traps";
          }
          leaf strict-bfd {
            type empty;
            description "Enable strict bfd over this interface";
          }
          container post-convergence-lfa {
            description "Protect interface using post-convergence backup path";
            presence "enable post-convergence-lfa";
            container node-protection {
              description "Compute backup path assuming node failure";
              presence "enable node-protection";
              leaf cost {
                type uint16 {
                  range "1 .. 65535";
                }
                description "Cost for node protection";
              }
            }
            leaf srlg-protection {
              type empty;
              description "Compute backup path assuming SRLG failure";
            }
            leaf fate-sharing-protection {
              type empty;
              description "Compute backup path assuming fate-sharing group failure";
            }
          }
          leaf te-metric {
            type uint32 {
              range "1 .. 4294967295";
            }
            description "Traffic engineering metric";
          }
          container ldp-synchronization {
            description "Advertise maximum metric until LDP is operational";
            presence "enable ldp-synchronization";
            uses ldp-sync-obj;
          }
          container ipv4-adjacency-segment {
            description "Configure ipv4 adjacency segment";
            container protected {
              description "Adjacency SID is eligible for protection";
              choice adjsid-type {
                case case_1 {
                  container index {
                    description "Adjacency SID indexed from SRGB";
                    leaf index-number {
                      type uint32 {
                        range "0 .. 199999";
                      }
                    }
                  }
                }
                case case_2 {
                  leaf label {
                    type uint32 {
                      range "16 .. 1048575";
                    }
                    description "Adjacency SID from static label pool";
                  }
                }
                case case_3 {
                  leaf dynamic {
                    type empty;
                    description "Dynamically allocate an adjacency segment";
                  }
                }
              }
            }
            container unprotected {
              description "Adjacency SID uneligible for protection";
              choice adjsid-type {
                case case_1 {
                  container index {
                    description "Adjacency SID indexed from SRGB";
                    leaf index-number {
                      type uint32 {
                        range "0 .. 199999";
                      }
                    }
                  }
                }
                case case_2 {
                  leaf label {
                    type uint32 {
                      range "16 .. 1048575";
                    }
                    description "Adjacency SID from static label pool";
                  }
                }
                case case_3 {
                  leaf dynamic {
                    type empty;
                    description "Dynamically allocate an adjacency segment";
                  }
                }
              }
            }
          }
          list lan-neighbor {
            description "Configuration specific to a LAN neighbor";
            key name;
            ordered-by user;
            leaf name {
              type "jt:ipaddr";
              description "Address of neighbor";
            }
            container ipv4-adjacency-segment {
              description "Configure ipv4 adjacency segment";
              container protected {
                description "Adjacency SID is eligible for protection";
                choice adjsid-type {
                  case case_1 {
                    container index {
                      description "Adjacency SID indexed from SRGB";
                      leaf index-number {
                        type uint32 {
                          range "0 .. 199999";
                        }
                      }
                    }
                  }
                  case case_2 {
                    leaf label {
                      type uint32 {
                        range "16 .. 1048575";
                      }
                      description "Adjacency SID from static label pool";
                    }
                  }
                  case case_3 {
                    leaf dynamic {
                      type empty;
                      description "Dynamically allocate an adjacency segment";
                    }
                  }
                }
              }
              container unprotected {
                description "Adjacency SID uneligible for protection";
                choice adjsid-type {
                  case case_1 {
                    container index {
                      description "Adjacency SID indexed from SRGB";
                      leaf index-number {
                        type uint32 {
                          range "0 .. 199999";
                        }
                      }
                    }
                  }
                  case case_2 {
                    leaf label {
                      type uint32 {
                        range "16 .. 1048575";
                      }
                      description "Adjacency SID from static label pool";
                    }
                  }
                  case case_3 {
                    leaf dynamic {
                      type empty;
                      description "Dynamically allocate an adjacency segment";
                    }
                  }
                }
              }
            }
          }
          leaf delay-metric {
            type uint32 {
              range "0 .. 16777215";
            }
            description "Delay metric";
            units microseconds;
          }
          container delay-measurement {
            description "Enable delay measurement";
            presence "enable delay-measurement";
            leaf probe-interval {
              type uint32 {
                range "1 .. 255";
              }
              description "Probe interval";
              units seconds;
            }
            leaf probe-count {
              type uint32 {
                range "1 .. 15";
              }
              description "Probe count";
            }
            container advertisement {
              description "Delay advertisement";
              container periodic {
                description "Periodic advertisement parameters";
                leaf threshold {
                  type uint32 {
                    range "0 .. 100";
                  }
                  description "Threshold";
                  units percentage;
                }
                leaf interval {
                  type uint32 {
                    range "30 .. 3600";
                  }
                  description "Interval";
                  units seconds;
                }
              }
              container accelerated {
                description "Accelerated advertisement parameters";
                presence "enable accelerated";
                leaf threshold {
                  type uint32 {
                    range "0 .. 100";
                  }
                  description "Threshold";
                  units percentage;
                }
              }
            }
          }
          container application-specific {
            description "Advertise application-specific TE attributes";
            list attribute-group {
              description "Link attribute group name";
              key name;
              max-elements 1;
              ordered-by user;
              leaf name {
                type string;
                description "Link attribute group name";
              }
              leaf te-metric {
                type uint32 {
                  range "1 .. 4294967295";
                }
                description "Traffic engineering metric for this attribute group";
              }
              leaf-list admin-group {
                type string;
                description "Administrative groups for this attribute-group";
                max-elements 16;
                ordered-by user;
              }
              leaf delay-metric {
                type uint32 {
                  range "0 .. 16777215";
                }
                description "Delay metric for this attribute-group";
                units microseconds;
              }
              leaf advertise-interface-delay {
                type empty;
                description "Use interface specific static/dynamic delay values as applicable in ASLA Sub-TLVs";
              }
              container application {
                description "Standard Applications part of this attribute-group";
                leaf flex-algorithm {
                  type empty;
                  description "Set X flag in standard application bit mask";
                }
              }
            }
          }
        }
        leaf no-context-identifier-advertisement {
          type empty;
          description "Disable context identifier advertisments in this area";
        }
        list peer-interface {
          description "Configuration for peer interface";
          key name;
          ordered-by user;
          leaf name {
            type string;
            description "Name of peer interface";
          }
          choice enable-disable {
            case case_1 {
              leaf disable {
                type empty;
                description "Disable OSPF on this control peer";
              }
            }
          }
          leaf retransmit-interval {
            type uint32 {
              range "1 .. 65535";
            }
            description "Retransmission interval (seconds)";
          }
          leaf transit-delay {
            type uint32 {
              range "1 .. 65535";
            }
            description "Transit delay (seconds)";
          }
          leaf hello-interval {
            type uint32 {
              range "1 .. 255";
            }
            description "Hello interval (seconds)";
          }
          leaf dead-interval {
            type uint32 {
              range "1 .. 65535";
            }
            description "Dead interval (seconds)";
          }
          leaf mtu {
            type uint32 {
              range "128 .. 65535";
            }
            description "Maximum OSPF packet size";
          }
          choice auth {
            case case_1 {
              container authentication {
                uses juniper-ospf-authentication;
              }
            }
            case case_2 {
              container authentication-key {
                description "Authentication key";
                status deprecated;
                leaf keyname {
                  type "jt:unreadable";
                  description "Authentication key value";
                }
                leaf key-id {
                  type uint32 {
                    range "0 .. 255";
                  }
                  description "Key ID for MD5 authentication";
                }
              }
            }
          }
          leaf demand-circuit {
            type empty;
            description "Interface functions as a demand circuit";
          }
          leaf flood-reduction {
            type empty;
            description "Enable flood reduction";
          }
          leaf no-neighbor-down-notification {
            type empty;
            description "Don't inform other protocols about neighbor down events";
          }
        }
        leaf no-source-packet-routing {
          type empty;
          description "Disable SPRING in this area";
        }
        list context-identifier {
          description "Configure context identifier in support of edge protection";
          key name;
          ordered-by user;
          leaf name {
            type "jt:ipv4addr";
            description "Context identifier";
          }
        }
        list label-switched-path {
          description "Configuration for advertisement of a label-switched path";
          key name;
          ordered-by user;
          leaf name {
            type string {
              length "1 .. 64";
            }
            description "Name of label-switched path to be advertised";
          }
          choice enable-disable {
            case case_1 {
              leaf disable {
                type empty;
                description "Disable OSPF on this label-switched path";
              }
            }
          }
          leaf metric {
            type uint16 {
              range "1 .. 65535";
            }
            description "Interface metric";
          }
          list topology {
            description "Topology specific attributes";
            key name;
            ordered-by user;
            leaf name {
              type string;
              description "Topology name";
            }
            leaf disable {
              type empty;
              description "Disable this topology";
            }
            leaf metric {
              type uint16 {
                range "1 .. 65535";
              }
              description "Topology metric";
            }
            container bandwidth-based-metrics {
              description "Configure bandwidth based metrics";
              list bandwidth {
                description "Bandwidth threshold";
                key name;
                leaf name {
                  type string;
                }
                leaf metric {
                  type uint16 {
                    range "1 .. 65535";
                  }
                  description "Metric associated with specified bandwidth";
                }
              }
            }
          }
        }
      }
      choice enable-disable {
        case case_1 {
          leaf disable {
            type empty;
            description "Disable OSPF";
          }
        }
      }
      container traceoptions {
        description "Trace options for OSPF";
        container file {
          description "Trace file options";
          leaf filename {
            type string {
              length "1 .. 1024";
            }
            description "Name of file in which to write trace information";
          }
          leaf replace {
            type empty;
            description "Replace trace file rather than appending to it";
            status deprecated;
          }
          leaf size {
            type string;
            description "Maximum trace file size";
          }
          leaf files {
            type uint32 {
              range "2 .. 1000";
            }
            default "10";
            description "Maximum number of trace files";
          }
          leaf no-stamp {
            type empty;
            description "Do not timestamp trace file";
            status deprecated;
          }
          choice world-readable-choice {
            leaf world-readable {
              type empty;
              description "Allow any user to read the log file";
            }
            leaf no-world-readable {
              type empty;
              description "Don't allow any user to read the log file";
            }
          }
        }
        list flag {
          description "Tracing parameters";
          key name;
          ordered-by user;
          leaf name {
            type enumeration {
              enum spf {
                description "Trace SPF calculations";
              }
              enum error {
                description "Trace errored packets";
              }
              enum event {
                description "Trace OSPF state machine events";
              }
              enum packet-dump {
                description "Dump the contents of selected packet types";
              }
              enum flooding {
                description "Trace LSA flooding";
              }
              enum lsa-analysis {
                description "Trace LSA analysis";
              }
              enum packets {
                description "Trace all OSPF packets";
              }
              enum hello {
                description "Trace hello packets";
              }
              enum database-description {
                description "Trace database description packets";
              }
              enum lsa-request {
                description "Trace LSA request packets";
              }
              enum lsa-update {
                description "Trace LSA update packets";
              }
              enum lsa-ack {
                description "Trace LSA acknowledgment packets";
              }
              enum ldp-synchronization {
                description "Trace synchronization between OSPF and LDP";
              }
              enum on-demand {
                description "Trace demand circuit extensions";
              }
              enum nsr-synchronization {
                description "Trace NSR synchronization events";
              }
              enum graceful-restart {
                description "Trace graceful restart";
              }
              enum restart-signaling {
                description "Trace restart signaling";
              }
              enum traffic-statistics {
                description "Trace Segment Routing Traffic Statistics";
              }
              enum backup-spf {
                description "Trace backup SPF (LFA) specific events";
              }
              enum source-packet-routing {
                description "Trace source packet routing (SPRING) events";
              }
              enum post-convergence-lfa {
                description "Trace post-convergence-lfa related events";
              }
              enum flex-algorithm {
                description "Trace flex-algorithm related events";
              }
              enum rmopd {
                description "Trace rmopd interactions";
              }
              enum route {
                description "Trace routing information";
              }
              enum normal {
                description "Trace normal events";
              }
              enum general {
                description "Trace general events";
              }
              enum state {
                description "Trace state transitions";
              }
              enum policy {
                description "Trace policy processing";
              }
              enum task {
                description "Trace routing protocol task processing";
              }
              enum timer {
                description "Trace routing protocol timer processing";
              }
              enum all {
                description "Trace everything";
              }
            }
          }
          leaf send {
            type empty;
            description "Trace transmitted packets";
          }
          leaf receive {
            type empty;
            description "Trace received packets";
          }
          leaf detail {
            type empty;
            description "Trace detailed information";
          }
          leaf disable {
            type empty;
            description "Disable this trace flag";
          }
        }
      }
      leaf prefix-export-limit {
        type uint32 {
          range "0 .. 4294967295";
        }
        description "Maximum number of prefixes that can be exported";
      }
      container rib-groups {
        description "Routing table groups for importing OSPF routes";
        leaf inet {
          type string;
          description "Name of the IPv4/v6 routing table group";
        }
        leaf inet3 {
          type string;
          description "Name of the IPv4/v6 inet.3 routing table group";
        }
      }
      leaf job-stats {
        type empty;
        description "Collect job statistics";
      }
      container overload {
        description "Set the overload mode (repel transit traffic)";
        presence "enable overload";
        leaf timeout {
          type uint32 {
            range "60 .. 3600";
          }
          description "Time after which overload mode is reset";
          units seconds;
        }
        leaf allow-route-leaking {
          type empty;
          description "Allow routes to be leaked when overload is configured";
        }
        leaf stub-network {
          type empty;
          description "Advertise Stub Network with maximum metric";
        }
        leaf intra-area-prefix {
          type empty;
          description "Advertise Intra Area Prefix with maximum metric";
        }
        leaf as-external {
          type empty;
          description "Advertise As External with maximum usable metric";
        }
      }
      container database-protection {
        description "Configure database protection attributes";
        presence "enable database-protection";
        leaf maximum-lsa {
          type uint32 {
            range "1 .. 1000000";
          }
          description "Maximum allowed non self-generated LSAs";
        }
        leaf warning-only {
          type empty;
          description "Emit only a warning when LSA maximum limit is exceeded";
        }
        leaf warning-threshold {
          type uint8 {
            range "30 .. 100";
          }
          description "Percentage of LSA maximum above which to trigger warning";
          units percent;
        }
        leaf ignore-count {
          type uint8 {
            range "1 .. 32";
          }
          description "Maximum number of times to go into ignore state";
        }
        leaf ignore-time {
          type uint16 {
            range "30 .. 3600";
          }
          description "Time to stay in ignore state and ignore all neighbors";
          units seconds;
        }
        leaf reset-time {
          type uint32 {
            range "60 .. 86400";
          }
          description "Time after which the ignore count gets reset to zero";
          units seconds;
        }
      }
      container graceful-restart {
        description "Configure graceful restart attributes";
        choice enable-disable {
          case case_1 {
            leaf disable {
              type empty;
              description "Disable OSPF graceful restart capability";
            }
          }
        }
        leaf restart-duration {
          type uint32 {
            range "1 .. 3600";
          }
          description "Time for all neighbors to become full";
          units seconds;
        }
        leaf notify-duration {
          type uint32 {
            range "1 .. 3600";
          }
          description "Time to send all max-aged grace LSAs";
          units seconds;
        }
        container helper-disable {
          description "Disable graceful restart helper capability";
          presence "enable helper-disable";
          choice disable-choices {
            case case_1 {
              leaf standard {
                type empty;
                description "Disable helper-mode for rfc3623 based GR";
              }
            }
            case case_2 {
              leaf restart-signaling {
                type empty;
                description "Disable helper mode for restart-signaling ";
              }
            }
            case case_3 {
              leaf both {
                type empty;
                description "Disable helper mode for both the types of GR";
              }
            }
          }
        }
        leaf no-strict-lsa-checking {
          type empty;
          description "Do not abort graceful helper mode upon LSA changes";
        }
      }
      leaf route-type-community {
        type enumeration {
          enum iana {
            description "BGP extended community value used is 0x0306";
          }
          enum vendor {
            description "Vendor BGP extended community value used is 0x8000";
          }
        }
        description "Specify BGP extended community value to encode OSPF route type";
      }
      container domain-id {
        description "Configure domain ID";
        choice domain_id_or_disable {
          case case_1 {
            leaf domain-id {
              type string;
              description "Domain ID";
            }
          }
          case case_2 {
            leaf disable {
              type empty;
              description "Disable domain ID";
            }
          }
        }
      }
      choice domain_vpn_tag_or_disable {
        case case_1 {
          leaf domain-vpn-tag {
            type uint32 {
              range "0 .. 4294967295";
            }
            description "Domain VPN tag for external LSA";
          }
        }
        case case_2 {
          leaf no-domain-vpn-tag {
            type empty;
            description "Disable domain VPN tag";
          }
        }
      }
      leaf preference {
        type uint32;
        description "Preference of internal routes";
      }
      leaf external-preference {
        type uint32;
        description "Preference of external routes";
      }
      leaf labeled-preference {
        type uint32;
        description "Preference of labeled routes";
      }
      leaf-list export {
        type "jt:policy-algebra";
        description "Export policy";
        ordered-by user;
      }
      leaf-list import {
        type "jt:policy-algebra";
        description "Import policy (for external routes or setting priority)";
        ordered-by user;
      }
      leaf reference-bandwidth {
        type string;
        description "Bandwidth for calculating metric defaults";
      }
      leaf lsa-refresh-interval {
        type uint32 {
          range "25 .. 50";
        }
        default "50";
        description "LSA refresh interval (minutes)";
      }
      leaf spf-delay {
        type uint32 {
          range "50 .. 8000";
        }
        description "Time to wait before running an SPF";
        status deprecated;
        units milliseconds;
      }
      leaf no-rfc-1583 {
        type empty;
        description "Disable RFC1583 compatibility";
      }
      leaf forwarding-address-to-broadcast {
        type empty;
        description "Set forwarding address in Type 5 LSA in broadcast network";
      }
      choice nssa-abr-option {
        case case_1 {
          leaf no-nssa-abr {
            type empty;
            description "Disable full NSSA functionality at ABR";
          }
        }
      }
      container sham-link {
        description "Configure parameters for sham links";
        presence "enable sham-link";
        leaf local {
          type "jt:ipaddr";
          description "Local sham link endpoint address";
        }
        leaf no-advertise-local {
          type empty;
          description "Don't advertise local sham link endpoint as stub in router LSA";
          status deprecated;
        }
      }
    }
    list topology {
      description "Topology parameters";
      key name;
      ordered-by user;
      leaf name {
        type string;
        description "Topology name";
      }
      leaf disable {
        type empty;
        description "Disable this topology";
      }
      leaf topology-id {
        type uint8 {
          range "32 .. 127";
        }
        description "Topology identifier";
      }
      leaf overload {
        type empty;
        description "Set the overload mode (repel transit traffic)";
      }
      leaf rib-group {
        type string;
        description "Routing table group for importing routes";
      }
      container spf-options {
        description "Configure options for SPF";
        container microloop-avoidance {
          description "Configure microloop avoidance mechanism";
          container post-convergence-path {
            description "Temporarily install post-convergence path for routes potentially affected by microloops";
            presence "enable post-convergence-path";
            leaf delay {
              type uint32 {
                range "500 .. 60000";
              }
              description "Time after which temporary post-convergence paths are removed";
              units milliseconds;
            }
            leaf maximum-labels {
              type uint32 {
                range "2 .. 8";
              }
              description "Maximum number of labels installed for post-convergence paths";
            }
          }
        }
        leaf delay {
          type uint32 {
            range "50 .. 8000";
          }
          description "Time to wait before running an SPF";
          units milliseconds;
        }
        leaf holddown {
          type uint32 {
            range "2000 .. 20000";
          }
          description "Time to hold down before running an SPF";
          units milliseconds;
        }
        leaf rapid-runs {
          type uint32 {
            range "1 .. 10";
          }
          description "Number of maximum rapid SPF runs before holddown";
        }
        leaf no-ignore-our-externals {
          type empty;
          description "Do not ignore self-generated external and NSSA LSAs";
        }
      }
      container backup-spf-options {
        description "Configure options for backup SPF";
        container remote-backup-calculation {
          description "Calculate Remote LFA backup nexthops";
          presence "enable remote-backup-calculation";
          container pq-nodes-nearest-to-source {
            description "PQ nodes selection based upon nearest to source";
            leaf percent {
              type uint32 {
                range "10 .. 100";
              }
              description "Selection percentage for nearest to source";
            }
          }
        }
        container use-post-convergence-lfa {
          description "Calculate post-convergence backup paths";
          presence "enable use-post-convergence-lfa";
          leaf maximum-labels {
            type uint32 {
              range "2 .. 8";
            }
            description "Maximum number of labels installed for post-convergence paths";
          }
          leaf maximum-backup-paths {
            type uint32 {
              range "1 .. 8";
            }
            description "Maximum number of equal-cost post-convergence paths installed";
          }
        }
        leaf use-source-packet-routing {
          type empty;
          description "Use spring backup paths for inet.0 routes";
        }
        leaf disable {
          type empty;
          description "Do not run backup SPF";
        }
        leaf no-install {
          type empty;
          description "Do not install backup nexthops into the RIB";
        }
        leaf downstream-paths-only {
          type empty;
          description "Use only downstream backup paths";
        }
        container per-prefix-calculation {
          description "Calculate backup nexthops for non-best prefix originators";
          leaf stubs {
            type empty;
            description "Per prefix calculation for stubs only";
          }
          leaf summary {
            type empty;
            description "Per prefix calculation for summary originators only";
          }
          leaf externals {
            type empty;
            description "Per prefix calculation for externals";
          }
          leaf all {
            type empty;
            description "Per prefix calculation for all";
          }
        }
        leaf node-link-degradation {
          type empty;
          description "Degrade to link protection when nodelink protection not available";
        }
      }
      leaf prefix-export-limit {
        type uint32 {
          range "0 .. 4294967295";
        }
        description "Maximum number of prefixes that can be exported";
      }
    }
    container spf-options {
      description "Configure options for SPF";
      container microloop-avoidance {
        description "Configure microloop avoidance mechanism";
        container post-convergence-path {
          description "Temporarily install post-convergence path for routes potentially affected by microloops";
          presence "enable post-convergence-path";
          leaf delay {
            type uint32 {
              range "500 .. 60000";
            }
            description "Time after which temporary post-convergence paths are removed";
            units milliseconds;
          }
          leaf maximum-labels {
            type uint32 {
              range "2 .. 8";
            }
            description "Maximum number of labels installed for post-convergence paths";
          }
        }
      }
      leaf delay {
        type uint32 {
          range "50 .. 8000";
        }
        description "Time to wait before running an SPF";
        units milliseconds;
      }
      leaf holddown {
        type uint32 {
          range "2000 .. 20000";
        }
        description "Time to hold down before running an SPF";
        units milliseconds;
      }
      leaf rapid-runs {
        type uint32 {
          range "1 .. 10";
        }
        description "Number of maximum rapid SPF runs before holddown";
      }
      leaf no-ignore-our-externals {
        type empty;
        description "Do not ignore self-generated external and NSSA LSAs";
      }
    }
    container backup-spf-options {
      description "Configure options for backup SPF";
      container remote-backup-calculation {
        description "Calculate Remote LFA backup nexthops";
        presence "enable remote-backup-calculation";
        container pq-nodes-nearest-to-source {
          description "PQ nodes selection based upon nearest to source";
          leaf percent {
            type uint32 {
              range "10 .. 100";
            }
            description "Selection percentage for nearest to source";
          }
        }
      }
      container use-post-convergence-lfa {
        description "Calculate post-convergence backup paths";
        presence "enable use-post-convergence-lfa";
        leaf maximum-labels {
          type uint32 {
            range "2 .. 8";
          }
          description "Maximum number of labels installed for post-convergence paths";
        }
        leaf maximum-backup-paths {
          type uint32 {
            range "1 .. 8";
          }
          description "Maximum number of equal-cost post-convergence paths installed";
        }
      }
      leaf use-source-packet-routing {
        type empty;
        description "Use spring backup paths for inet.0 routes";
      }
      leaf disable {
        type empty;
        description "Do not run backup SPF";
      }
      leaf no-install {
        type empty;
        description "Do not install backup nexthops into the RIB";
      }
      leaf downstream-paths-only {
        type empty;
        description "Use only downstream backup paths";
      }
      container per-prefix-calculation {
        description "Calculate backup nexthops for non-best prefix originators";
        leaf stubs {
          type empty;
          description "Per prefix calculation for stubs only";
        }
        leaf summary {
          type empty;
          description "Per prefix calculation for summary originators only";
        }
        leaf externals {
          type empty;
          description "Per prefix calculation for externals";
        }
        leaf all {
          type empty;
          description "Per prefix calculation for all";
        }
      }
      leaf node-link-degradation {
        type empty;
        description "Degrade to link protection when nodelink protection not available";
      }
    }
    container traffic-engineering {
      description "Configure traffic engineering attributes";
      presence "enable traffic-engineering";
      leaf no-topology {
        type empty;
        description "Disable dissemination of TE link-state topology information";
      }
      leaf multicast-rpf-routes {
        type empty;
        description "Install routes for multicast RPF checks into inet.2";
      }
      leaf l3-unicast-topology {
        type empty;
        description "Download IGP topology into TED";
      }
      container ignore-lsp-metrics {
        description "Ignore label-switched path metrics when doing shortcuts";
        presence "enable ignore-lsp-metrics";
        leaf unconfigured-only {
          type empty;
          description "Ignore lsp metrics for unconfigured only";
        }
      }
      container shortcuts {
        description "Use label-switched paths as next hops, if possible";
        presence "enable shortcuts";
        leaf ignore-lsp-metrics {
          type empty;
          description "Ignore label-switched path metrics when doing shortcuts";
          status deprecated;
        }
        leaf lsp-metric-into-summary {
          type empty;
          description "Advertise LSP metric into summary LSAs";
        }
        list family {
          description "Address family specific traffic-engineering attributes";
          key name;
          ordered-by user;
          leaf name {
            type enumeration {
              enum inet {
                description "IPv4 family";
              }
              enum inet-mpls {
                description "IPv4-MPLS family";
              }
            }
          }
        }
      }
      leaf advertise-unnumbered-interfaces {
        type empty;
        description "Advertise unnumbered interfaces";
      }
      leaf credibility-protocol-preference {
        type empty;
        description "TED protocol credibility follows protocol preference";
      }
      container advertisement {
        description "Advertise TE parameters even if RSVP is not turned on";
        leaf always {
          type empty;
          description "Advertise TE parameters in TE LSAs";
        }
      }
      container tunnel-source-protocol {
        description "Protocols from which to pick label-switched paths";
        container rsvp {
          description "Pick label-switched paths from rsvp";
          presence "enable rsvp";
          leaf preference {
            type uint32 {
              range "1 .. 255";
            }
            description "Preference for label-switched paths from this protocol";
          }
        }
        container spring-te {
          description "Pick label-switched paths from spring-te";
          presence "enable spring-te";
          leaf preference {
            type uint32 {
              range "1 .. 255";
            }
            description "Preference for label-switched paths from this protocol";
          }
        }
      }
    }
    container source-packet-routing {
      description "Enable source packet routing (SPRING)";
      presence "enable source-packet-routing";
      container adjacency-segment {
        description "Attributes for adjacency segments in spring";
        leaf hold-time {
          type uint32 {
            range "180000 .. 900000";
          }
          description "Retain time of Adjacency segment after isolating from an interface";
        }
      }
      leaf-list prefix-segment {
        type "jt:policy-algebra";
        description "Prefix Segment policy";
        ordered-by user;
      }
      leaf explicit-null {
        type empty;
        description "Set E and P bits in all Prefix SID advertisements";
      }
      container node-segment {
        description "Enable support for Node segments in SPRING";
        presence "enable node-segment";
        leaf ipv4-index {
          type uint32 {
            range "0 .. 199999";
          }
          description "Set ipv4 node segment index";
        }
        leaf index-range {
          type uint32 {
            range "32 .. 16385";
          }
          description "Set range of node segment indices allowed";
        }
      }
      container srgb {
        description "Set the SRGB global block in SPRING";
        leaf start-label {
          type uint32;
          description "Start range for SRGB label block";
        }
        leaf index-range {
          type uint32;
          description "Index to the SRGB start label block";
        }
      }
      leaf mapping-server {
        type string;
        description "Mapping server name";
      }
      leaf install-prefix-sid-for-best-route {
        type empty;
        description "For best route install a exact prefix sid route";
      }
      leaf ldp-stitching {
        type empty;
        description "Enable SR to LDP stitching";
      }
      leaf-list flex-algorithm {
        type uint32 {
          range "128 .. 255";
        }
        description "Flex-algorithms we would like to participate in";
        max-elements 16;
      }
      leaf strict-asla-based-flex-algorithm {
        type empty;
        description "Flex-Algorithm to ignore links not having ASLA sub-TLVs";
      }
      container sensor-based-stats {
        description "Configure sensor based stats in SPRING";
        container per-interface-per-member-link {
          description "Configure sensor based stats per nexthop";
          leaf ingress {
            type empty;
            description "Enable sensor based stats on ingress interface";
          }
          leaf egress {
            type empty;
            description "Enable sensor based stats on egress interface";
          }
        }
        container per-sid {
          description "Configure sensor based stats per spring route";
          leaf ingress {
            type empty;
            description "Enable sensor based stats for per-sid ingress accounting";
          }
          leaf egress {
            type empty;
            description "Enable sensor based stats for IP-MPLS egress accounting";
          }
        }
      }
    }
    list area {
      description "Configure an OSPF area";
      key name;
      ordered-by user;
      leaf name {
        type "jt:areaid";
        description "Area ID";
      }
      choice stub-option {
        case case_1 {
          container stub {
            description "Configure a stub area";
            presence "enable stub";
            leaf default-metric {
              type uint32 {
                range "1 .. 16777215";
              }
              description "Metric for the default route in this stub area";
            }
            choice summaries-choice {
              leaf summaries {
                type empty;
                description "Flood summary LSAs into this stub area";
              }
              leaf no-summaries {
                type empty;
                description "Don't flood summary LSAs into this stub area";
              }
            }
          }
        }
        case case_2 {
          container nssa {
            description "Configure a not-so-stubby area";
            presence "enable nssa";
            container default-lsa {
              description "Configure a default LSA";
              presence "enable default-lsa";
              leaf default-metric {
                type uint32 {
                  range "1 .. 16777215";
                }
                description "Metric for the default route in this area";
              }
              leaf metric-type {
                type uint32 {
                  range "1 .. 2";
                }
                description "External metric type for the default type 7 LSA";
              }
              leaf type-7 {
                type empty;
                description "Flood type 7 default LSA if no-summaries is configured";
              }
            }
            leaf default-metric {
              type uint32 {
                range "1 .. 16777215";
              }
              description "Metric for the default route in this area";
              status deprecated;
            }
            leaf metric-type {
              type uint32 {
                range "1 .. 2";
              }
              description "External metric type for the default type 7 LSA";
              status deprecated;
            }
            choice summaries-choice {
              leaf summaries {
                type empty;
                description "Flood summary LSAs into this NSSA area";
              }
              leaf no-summaries {
                type empty;
                description "Don't flood summary LSAs into this NSSA area";
              }
            }
            list area-range {
              description "Configure NSSA area ranges";
              key name;
              ordered-by user;
              leaf name {
                type "jt:ipprefix";
                description "Range to summarize NSSA routes in this area";
              }
              leaf restrict {
                type empty;
                description "Restrict advertisement of this area range";
              }
              leaf exact {
                type empty;
                description "Enforce exact match for advertisement of this area range";
              }
              container override-metric {
                description "Override the dynamic metric for this area-range";
                presence "enable override-metric";
                leaf metric {
                  type uint32 {
                    range "1 .. 16777215";
                  }
                  description "Metric value";
                }
                leaf metric-type {
                  type uint32 {
                    range "1 .. 2";
                  }
                  default "1";
                  description "Set the metric type for the override metric";
                }
              }
            }
          }
        }
      }
      list area-range {
        description "Configure area ranges";
        key name;
        ordered-by user;
        leaf name {
          type "jt:ipprefix";
          description "Range to summarize routes in this area";
        }
        leaf restrict {
          type empty;
          description "Restrict advertisement of this area range";
        }
        leaf exact {
          type empty;
          description "Enforce exact match for advertisement of this area range";
        }
        leaf override-metric {
          type uint32 {
            range "1 .. 16777215";
          }
          description "Override the dynamic metric for this area-range";
        }
      }
      leaf-list network-summary-export {
        type "jt:policy-algebra";
        description "Export policy for Type 3 Summary LSAs";
        ordered-by user;
      }
      leaf-list network-summary-import {
        type "jt:policy-algebra";
        description "Import policy for Type 3 Summary LSAs";
        ordered-by user;
      }
      leaf-list inter-area-prefix-export {
        type "jt:policy-algebra";
        description "Export policy for Inter Area Prefix LSAs";
        ordered-by user;
      }
      leaf-list inter-area-prefix-import {
        type "jt:policy-algebra";
        description "Import policy for Inter Area Prefix LSAs";
        ordered-by user;
      }
      leaf authentication-type {
        type enumeration {
          enum none {
            description "No authentication";
            status deprecated;
          }
          enum simple {
            description "Simple password authentication";
            status deprecated;
          }
          enum md5 {
            description "MD5 authentication";
            status deprecated;
          }
        }
        description "Authentication type";
        status deprecated;
      }
      list virtual-link {
        description "Configure virtual links";
        key "neighbor-id transit-area";
        ordered-by user;
        leaf neighbor-id {
          type "jt:ipv4addr";
          description "Router ID of a virtual neighbor";
        }
        leaf transit-area {
          type "jt:areaid";
          description "Transit area in common with virtual neighbor";
        }
        choice enable-disable {
          case case_1 {
            leaf disable {
              type empty;
              description "Disable this virtual link";
            }
          }
        }
        leaf retransmit-interval {
          type uint32 {
            range "1 .. 65535";
          }
          description "Retransmission interval (seconds)";
        }
        leaf transit-delay {
          type uint32 {
            range "1 .. 65535";
          }
          description "Transit delay (seconds)";
        }
        leaf hello-interval {
          type uint32 {
            range "1 .. 255";
          }
          description "Hello interval (seconds)";
        }
        leaf dead-interval {
          type uint32 {
            range "1 .. 65535";
          }
          description "Dead interval (seconds)";
        }
        leaf mtu {
          type uint32 {
            range "128 .. 65535";
          }
          description "Maximum OSPF packet size";
        }
        choice auth {
          case case_1 {
            container authentication {
              uses juniper-ospf-authentication;
            }
          }
          case case_2 {
            container authentication-key {
              description "Authentication key";
              status deprecated;
              leaf keyname {
                type "jt:unreadable";
                description "Authentication key value";
              }
              leaf key-id {
                type uint32 {
                  range "0 .. 255";
                }
                description "Key ID for MD5 authentication";
              }
            }
          }
        }
        leaf demand-circuit {
          type empty;
          description "Interface functions as a demand circuit";
        }
        leaf flood-reduction {
          type empty;
          description "Enable flood reduction";
        }
        leaf no-neighbor-down-notification {
          type empty;
          description "Don't inform other protocols about neighbor down events";
        }
        leaf ipsec-sa {
          type string {
            length "1 .. 32";
          }
          description "IPSec security association name";
        }
        list topology {
          description "Topology specific attributes";
          key name;
          ordered-by user;
          leaf name {
            type string;
            description "Topology name";
          }
          leaf disable {
            type empty;
            description "Disable this topology";
          }
          leaf metric {
            type uint16 {
              range "1 .. 65535";
            }
            description "Topology metric";
          }
          container bandwidth-based-metrics {
            description "Configure bandwidth based metrics";
            list bandwidth {
              description "Bandwidth threshold";
              key name;
              leaf name {
                type string;
              }
              leaf metric {
                type uint16 {
                  range "1 .. 65535";
                }
                description "Metric associated with specified bandwidth";
              }
            }
          }
        }
      }
      list sham-link-remote {
        description "Configure parameters for remote sham link endpoint";
        key name;
        ordered-by user;
        leaf name {
          type "jt:ipaddr";
          description "Remote sham link endpoint address";
        }
        leaf metric {
          type uint16 {
            range "1 .. 65535";
          }
          description "Sham link metric";
        }
        leaf ipsec-sa {
          type string {
            length "1 .. 32";
          }
          description "IPSec security association name";
        }
        leaf demand-circuit {
          type empty;
          description "Interface functions as a demand circuit";
        }
        leaf flood-reduction {
          type empty;
          description "Enable flood reduction";
        }
        list topology {
          description "Topology specific attributes";
          key name;
          ordered-by user;
          leaf name {
            type string;
            description "Topology name";
          }
          leaf disable {
            type empty;
            description "Disable this topology";
          }
          leaf metric {
            type uint16 {
              range "1 .. 65535";
            }
            description "Topology metric";
          }
          container bandwidth-based-metrics {
            description "Configure bandwidth based metrics";
            list bandwidth {
              description "Bandwidth threshold";
              key name;
              leaf name {
                type string;
              }
              leaf metric {
                type uint16 {
                  range "1 .. 65535";
                }
                description "Metric associated with specified bandwidth";
              }
            }
          }
        }
      }
      list interface {
        description "Include an interface in this area";
        key name;
        ordered-by user;
        leaf name {
          type "jt:ipv4addr-or-interface";
          description "Interface name";
        }
        choice enable-disable {
          case case_1 {
            leaf disable {
              type empty;
              description "Disable OSPF on this interface";
            }
          }
        }
        leaf interface-type {
          type enumeration {
            enum nbma {
              description "Nonbroadcast multiaccess";
            }
            enum p2mp {
              description "Point-to-multipoint NBMA";
            }
            enum p2p {
              description "Point-to-point";
            }
            enum p2mp-over-lan {
              description "Point-to-multipoint over LAN mode";
            }
          }
          description "Type of interface";
        }
        choice protection-type {
          case case_1 {
            leaf link-protection {
              type empty;
              description "Protect interface from link faults only";
            }
          }
          case case_2 {
            leaf node-link-protection {
              type empty;
              description "Protect interface from both link and node faults";
            }
          }
        }
        leaf no-eligible-backup {
          type empty;
          description "Not eligible to backup traffic from protected interfaces";
        }
        leaf no-eligible-remote-backup {
          type empty;
          description "Not eligible for Remote-LFA backup traffic from protected interfaces";
        }
        container passive {
          description "Do not run OSPF, but advertise it";
          presence "enable passive";
          container traffic-engineering {
            description "Advertise TE link information";
            leaf remote-node-id {
              type "jt:ipaddr";
              description "Remote address of the link";
            }
            leaf remote-node-router-id {
              type "jt:ipv4addr";
              description "TE Router-ID of the remote node";
            }
          }
        }
        leaf secondary {
          type empty;
          description "Treat interface as secondary";
        }
        leaf own-router-lsa {
          type empty;
          description "Generate a separate router LSA for this interface";
        }
        container bandwidth-based-metrics {
          description "Configure bandwidth based metrics";
          list bandwidth {
            description "Bandwidth threshold";
            key name;
            leaf name {
              type string;
            }
            leaf metric {
              type uint16 {
                range "1 .. 65535";
              }
              description "Metric associated with specified bandwidth";
            }
          }
        }
        leaf metric {
          type uint16 {
            range "1 .. 65535";
          }
          description "Interface metric";
        }
        leaf priority {
          type uint32 {
            range "0 .. 255";
          }
          description "Designated router priority";
        }
        leaf retransmit-interval {
          type uint32 {
            range "1 .. 65535";
          }
          description "Retransmission interval (seconds)";
        }
        leaf transit-delay {
          type uint32 {
            range "1 .. 65535";
          }
          description "Transit delay (seconds)";
        }
        leaf hello-interval {
          type uint32 {
            range "1 .. 255";
          }
          description "Hello interval (seconds)";
        }
        leaf dead-interval {
          type uint32 {
            range "1 .. 65535";
          }
          description "Dead interval (seconds)";
        }
        leaf mtu {
          type uint32 {
            range "128 .. 65535";
          }
          description "Maximum OSPF packet size";
        }
        choice auth {
          case case_1 {
            container authentication {
              uses juniper-ospf-authentication;
            }
          }
          case case_2 {
            container authentication-key {
              description "Authentication key";
              status deprecated;
              leaf keyname {
                type "jt:unreadable";
                description "Authentication key value";
              }
              leaf key-id {
                type uint32 {
                  range "0 .. 255";
                }
                description "Key ID for MD5 authentication";
              }
            }
          }
        }
        leaf demand-circuit {
          type empty;
          description "Interface functions as a demand circuit";
        }
        leaf flood-reduction {
          type empty;
          description "Enable flood reduction";
        }
        leaf no-neighbor-down-notification {
          type empty;
          description "Don't inform other protocols about neighbor down events";
        }
        leaf ipsec-sa {
          type string {
            length "1 .. 32";
          }
          description "IPSec security association name";
        }
        list topology {
          description "Topology specific attributes";
          key name;
          ordered-by user;
          leaf name {
            type string;
            description "Topology name";
          }
          leaf disable {
            type empty;
            description "Disable this topology";
          }
          leaf metric {
            type uint16 {
              range "1 .. 65535";
            }
            description "Topology metric";
          }
          container bandwidth-based-metrics {
            description "Configure bandwidth based metrics";
            list bandwidth {
              description "Bandwidth threshold";
              key name;
              leaf name {
                type string;
              }
              leaf metric {
                type uint16 {
                  range "1 .. 65535";
                }
                description "Metric associated with specified bandwidth";
              }
            }
          }
        }
        leaf transmit-interval {
          type uint32 {
            range "1 .. 4294967295";
          }
          description "OSPF packet transmit interval (milliseconds)";
          status deprecated;
        }
        container bfd-liveness-detection {
          description "Bidirectional Forwarding Detection options";
          leaf version {
            type enumeration {
              enum 0 {
                description "BFD version 0 (deprecated)";
              }
              enum 1 {
                description "BFD version 1";
              }
              enum automatic {
                description "Choose BFD version automatically";
              }
            }
            default "automatic";
            description "BFD protocol version number";
          }
          leaf minimum-interval {
            type uint32 {
              range "1 .. 255000";
            }
            description "Minimum transmit and receive interval";
            units milliseconds;
          }
          leaf minimum-transmit-interval {
            type uint32 {
              range "1 .. 255000";
            }
            description "Minimum transmit interval";
            status deprecated;
            units milliseconds;
          }
          leaf minimum-receive-interval {
            type uint32 {
              range "1 .. 255000";
            }
            description "Minimum receive interval";
            units milliseconds;
          }
          leaf multiplier {
            type uint32 {
              range "1 .. 255";
            }
            default "3";
            description "Detection time multiplier";
          }
          leaf inline-disable {
            type empty;
            description "Disable inline mode for this BFD session";
          }
          leaf pdu-size {
            type uint32 {
              range "24 .. 9000";
            }
            default "24";
            description "BFD transport protocol payload size";
          }
          choice adaptation-choice {
            case case_1 {
              leaf no-adaptation {
                type empty;
                description "Disable adaptation";
              }
            }
          }
          container transmit-interval {
            description "Transmit-interval options";
            leaf minimum-interval {
              type uint32 {
                range "1 .. 255000";
              }
              description "Minimum transmit interval";
              units milliseconds;
            }
            leaf threshold {
              type uint32;
              description "High transmit interval triggering a trap";
              units milliseconds;
            }
          }
          container detection-time {
            description "Detection-time options";
            leaf threshold {
              type uint32;
              description "High detection-time triggering a trap";
              units milliseconds;
            }
          }
          container authentication {
            description "Authentication options";
            leaf key-chain {
              type string;
              description "Key chain name";
            }
            leaf algorithm {
              type enumeration {
                enum simple-password {
                  description "Simple password";
                }
                enum keyed-md5 {
                  description "Keyed message Digest 5";
                }
                enum meticulous-keyed-md5 {
                  description "Meticulous keyed message Digest 5";
                }
                enum keyed-sha-1 {
                  description "Keyed secure hash algorithm (SHA1) ";
                }
                enum meticulous-keyed-sha-1 {
                  description "Meticulous keyed secure hash algorithm (SHA1) ";
                }
              }
              description "Algorithm name";
            }
            leaf loose-check {
              type empty;
              description "Verify authentication only if authentication is negotiated";
            }
          }
          container echo {
            description "Echo mode parameters";
            leaf minimum-interval {
              type uint32 {
                range "100 .. 255000";
              }
              description "Minimum transmit and receive interval";
              units milliseconds;
            }
          }
          container echo-lite {
            description "Echo-lite more parameters";
            leaf minimum-interval {
              type uint32 {
                range "100 .. 255000";
              }
              description "Minimum transmit and receive interval";
              units milliseconds;
            }
          }
          leaf full-neighbors-only {
            type empty;
            description "Setup BFD sessions only to Full neighbors";
          }
          leaf holddown-interval {
            type uint32 {
              range "0 .. 255000";
            }
            description "Time to hold the session-UP notification to the client";
            units milliseconds;
          }
        }
        leaf dynamic-neighbors {
          type empty;
          description "Learn neighbors dynamically on a p2mp interface";
        }
        leaf no-advertise-adjacency-segment {
          type empty;
          description "Do not advertise an adjacency segment for this interface";
        }
        list neighbor {
          description "NBMA neighbor";
          key name;
          ordered-by user;
          leaf name {
            type "jt:ipaddr";
            description "Address of neighbor";
          }
          leaf eligible {
            type empty;
            description "Eligible to be DR on an NBMA network";
          }
        }
        leaf poll-interval {
          type uint32 {
            range "1 .. 65535";
          }
          description "Poll interval for NBMA interfaces";
        }
        leaf no-interface-state-traps {
          type empty;
          description "Do not send interface state change traps";
        }
        leaf strict-bfd {
          type empty;
          description "Enable strict bfd over this interface";
        }
        container post-convergence-lfa {
          description "Protect interface using post-convergence backup path";
          presence "enable post-convergence-lfa";
          container node-protection {
            description "Compute backup path assuming node failure";
            presence "enable node-protection";
            leaf cost {
              type uint16 {
                range "1 .. 65535";
              }
              description "Cost for node protection";
            }
          }
          leaf srlg-protection {
            type empty;
            description "Compute backup path assuming SRLG failure";
          }
          leaf fate-sharing-protection {
            type empty;
            description "Compute backup path assuming fate-sharing group failure";
          }
        }
        leaf te-metric {
          type uint32 {
            range "1 .. 4294967295";
          }
          description "Traffic engineering metric";
        }
        container ldp-synchronization {
          description "Advertise maximum metric until LDP is operational";
          presence "enable ldp-synchronization";
          uses ldp-sync-obj;
        }
        container ipv4-adjacency-segment {
          description "Configure ipv4 adjacency segment";
          container protected {
            description "Adjacency SID is eligible for protection";
            choice adjsid-type {
              case case_1 {
                container index {
                  description "Adjacency SID indexed from SRGB";
                  leaf index-number {
                    type uint32 {
                      range "0 .. 199999";
                    }
                  }
                }
              }
              case case_2 {
                leaf label {
                  type uint32 {
                    range "16 .. 1048575";
                  }
                  description "Adjacency SID from static label pool";
                }
              }
              case case_3 {
                leaf dynamic {
                  type empty;
                  description "Dynamically allocate an adjacency segment";
                }
              }
            }
          }
          container unprotected {
            description "Adjacency SID uneligible for protection";
            choice adjsid-type {
              case case_1 {
                container index {
                  description "Adjacency SID indexed from SRGB";
                  leaf index-number {
                    type uint32 {
                      range "0 .. 199999";
                    }
                  }
                }
              }
              case case_2 {
                leaf label {
                  type uint32 {
                    range "16 .. 1048575";
                  }
                  description "Adjacency SID from static label pool";
                }
              }
              case case_3 {
                leaf dynamic {
                  type empty;
                  description "Dynamically allocate an adjacency segment";
                }
              }
            }
          }
        }
        list lan-neighbor {
          description "Configuration specific to a LAN neighbor";
          key name;
          ordered-by user;
          leaf name {
            type "jt:ipaddr";
            description "Address of neighbor";
          }
          container ipv4-adjacency-segment {
            description "Configure ipv4 adjacency segment";
            container protected {
              description "Adjacency SID is eligible for protection";
              choice adjsid-type {
                case case_1 {
                  container index {
                    description "Adjacency SID indexed from SRGB";
                    leaf index-number {
                      type uint32 {
                        range "0 .. 199999";
                      }
                    }
                  }
                }
                case case_2 {
                  leaf label {
                    type uint32 {
                      range "16 .. 1048575";
                    }
                    description "Adjacency SID from static label pool";
                  }
                }
                case case_3 {
                  leaf dynamic {
                    type empty;
                    description "Dynamically allocate an adjacency segment";
                  }
                }
              }
            }
            container unprotected {
              description "Adjacency SID uneligible for protection";
              choice adjsid-type {
                case case_1 {
                  container index {
                    description "Adjacency SID indexed from SRGB";
                    leaf index-number {
                      type uint32 {
                        range "0 .. 199999";
                      }
                    }
                  }
                }
                case case_2 {
                  leaf label {
                    type uint32 {
                      range "16 .. 1048575";
                    }
                    description "Adjacency SID from static label pool";
                  }
                }
                case case_3 {
                  leaf dynamic {
                    type empty;
                    description "Dynamically allocate an adjacency segment";
                  }
                }
              }
            }
          }
        }
        leaf delay-metric {
          type uint32 {
            range "0 .. 16777215";
          }
          description "Delay metric";
          units microseconds;
        }
        container delay-measurement {
          description "Enable delay measurement";
          presence "enable delay-measurement";
          leaf probe-interval {
            type uint32 {
              range "1 .. 255";
            }
            description "Probe interval";
            units seconds;
          }
          leaf probe-count {
            type uint32 {
              range "1 .. 15";
            }
            description "Probe count";
          }
          container advertisement {
            description "Delay advertisement";
            container periodic {
              description "Periodic advertisement parameters";
              leaf threshold {
                type uint32 {
                  range "0 .. 100";
                }
                description "Threshold";
                units percentage;
              }
              leaf interval {
                type uint32 {
                  range "30 .. 3600";
                }
                description "Interval";
                units seconds;
              }
            }
            container accelerated {
              description "Accelerated advertisement parameters";
              presence "enable accelerated";
              leaf threshold {
                type uint32 {
                  range "0 .. 100";
                }
                description "Threshold";
                units percentage;
              }
            }
          }
        }
        container application-specific {
          description "Advertise application-specific TE attributes";
          list attribute-group {
            description "Link attribute group name";
            key name;
            max-elements 1;
            ordered-by user;
            leaf name {
              type string;
              description "Link attribute group name";
            }
            leaf te-metric {
              type uint32 {
                range "1 .. 4294967295";
              }
              description "Traffic engineering metric for this attribute group";
            }
            leaf-list admin-group {
              type string;
              description "Administrative groups for this attribute-group";
              max-elements 16;
              ordered-by user;
            }
            leaf delay-metric {
              type uint32 {
                range "0 .. 16777215";
              }
              description "Delay metric for this attribute-group";
              units microseconds;
            }
            leaf advertise-interface-delay {
              type empty;
              description "Use interface specific static/dynamic delay values as applicable in ASLA Sub-TLVs";
            }
            container application {
              description "Standard Applications part of this attribute-group";
              leaf flex-algorithm {
                type empty;
                description "Set X flag in standard application bit mask";
              }
            }
          }
        }
      }
      leaf no-context-identifier-advertisement {
        type empty;
        description "Disable context identifier advertisments in this area";
      }
      list peer-interface {
        description "Configuration for peer interface";
        key name;
        ordered-by user;
        leaf name {
          type string;
          description "Name of peer interface";
        }
        choice enable-disable {
          case case_1 {
            leaf disable {
              type empty;
              description "Disable OSPF on this control peer";
            }
          }
        }
        leaf retransmit-interval {
          type uint32 {
            range "1 .. 65535";
          }
          description "Retransmission interval (seconds)";
        }
        leaf transit-delay {
          type uint32 {
            range "1 .. 65535";
          }
          description "Transit delay (seconds)";
        }
        leaf hello-interval {
          type uint32 {
            range "1 .. 255";
          }
          description "Hello interval (seconds)";
        }
        leaf dead-interval {
          type uint32 {
            range "1 .. 65535";
          }
          description "Dead interval (seconds)";
        }
        leaf mtu {
          type uint32 {
            range "128 .. 65535";
          }
          description "Maximum OSPF packet size";
        }
        choice auth {
          case case_1 {
            container authentication {
              uses juniper-ospf-authentication;
            }
          }
          case case_2 {
            container authentication-key {
              description "Authentication key";
              status deprecated;
              leaf keyname {
                type "jt:unreadable";
                description "Authentication key value";
              }
              leaf key-id {
                type uint32 {
                  range "0 .. 255";
                }
                description "Key ID for MD5 authentication";
              }
            }
          }
        }
        leaf demand-circuit {
          type empty;
          description "Interface functions as a demand circuit";
        }
        leaf flood-reduction {
          type empty;
          description "Enable flood reduction";
        }
        leaf no-neighbor-down-notification {
          type empty;
          description "Don't inform other protocols about neighbor down events";
        }
      }
      leaf no-source-packet-routing {
        type empty;
        description "Disable SPRING in this area";
      }
      list context-identifier {
        description "Configure context identifier in support of edge protection";
        key name;
        ordered-by user;
        leaf name {
          type "jt:ipv4addr";
          description "Context identifier";
        }
      }
      list label-switched-path {
        description "Configuration for advertisement of a label-switched path";
        key name;
        ordered-by user;
        leaf name {
          type string {
            length "1 .. 64";
          }
          description "Name of label-switched path to be advertised";
        }
        choice enable-disable {
          case case_1 {
            leaf disable {
              type empty;
              description "Disable OSPF on this label-switched path";
            }
          }
        }
        leaf metric {
          type uint16 {
            range "1 .. 65535";
          }
          description "Interface metric";
        }
        list topology {
          description "Topology specific attributes";
          key name;
          ordered-by user;
          leaf name {
            type string;
            description "Topology name";
          }
          leaf disable {
            type empty;
            description "Disable this topology";
          }
          leaf metric {
            type uint16 {
              range "1 .. 65535";
            }
            description "Topology metric";
          }
          container bandwidth-based-metrics {
            description "Configure bandwidth based metrics";
            list bandwidth {
              description "Bandwidth threshold";
              key name;
              leaf name {
                type string;
              }
              leaf metric {
                type uint16 {
                  range "1 .. 65535";
                }
                description "Metric associated with specified bandwidth";
              }
            }
          }
        }
      }
    }
    choice enable-disable {
      case case_1 {
        leaf disable {
          type empty;
          description "Disable OSPF";
        }
      }
    }
    container traceoptions {
      description "Trace options for OSPF";
      container file {
        description "Trace file options";
        leaf filename {
          type string {
            length "1 .. 1024";
          }
          description "Name of file in which to write trace information";
        }
        leaf replace {
          type empty;
          description "Replace trace file rather than appending to it";
          status deprecated;
        }
        leaf size {
          type string;
          description "Maximum trace file size";
        }
        leaf files {
          type uint32 {
            range "2 .. 1000";
          }
          default "10";
          description "Maximum number of trace files";
        }
        leaf no-stamp {
          type empty;
          description "Do not timestamp trace file";
          status deprecated;
        }
        choice world-readable-choice {
          leaf world-readable {
            type empty;
            description "Allow any user to read the log file";
          }
          leaf no-world-readable {
            type empty;
            description "Don't allow any user to read the log file";
          }
        }
      }
      list flag {
        description "Tracing parameters";
        key name;
        ordered-by user;
        leaf name {
          type enumeration {
            enum spf {
              description "Trace SPF calculations";
            }
            enum error {
              description "Trace errored packets";
            }
            enum event {
              description "Trace OSPF state machine events";
            }
            enum packet-dump {
              description "Dump the contents of selected packet types";
            }
            enum flooding {
              description "Trace LSA flooding";
            }
            enum lsa-analysis {
              description "Trace LSA analysis";
            }
            enum packets {
              description "Trace all OSPF packets";
            }
            enum hello {
              description "Trace hello packets";
            }
            enum database-description {
              description "Trace database description packets";
            }
            enum lsa-request {
              description "Trace LSA request packets";
            }
            enum lsa-update {
              description "Trace LSA update packets";
            }
            enum lsa-ack {
              description "Trace LSA acknowledgment packets";
            }
            enum ldp-synchronization {
              description "Trace synchronization between OSPF and LDP";
            }
            enum on-demand {
              description "Trace demand circuit extensions";
            }
            enum nsr-synchronization {
              description "Trace NSR synchronization events";
            }
            enum graceful-restart {
              description "Trace graceful restart";
            }
            enum restart-signaling {
              description "Trace restart signaling";
            }
            enum traffic-statistics {
              description "Trace Segment Routing Traffic Statistics";
            }
            enum backup-spf {
              description "Trace backup SPF (LFA) specific events";
            }
            enum source-packet-routing {
              description "Trace source packet routing (SPRING) events";
            }
            enum post-convergence-lfa {
              description "Trace post-convergence-lfa related events";
            }
            enum flex-algorithm {
              description "Trace flex-algorithm related events";
            }
            enum rmopd {
              description "Trace rmopd interactions";
            }
            enum route {
              description "Trace routing information";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
        leaf send {
          type empty;
          description "Trace transmitted packets";
        }
        leaf receive {
          type empty;
          description "Trace received packets";
        }
        leaf detail {
          type empty;
          description "Trace detailed information";
        }
        leaf disable {
          type empty;
          description "Disable this trace flag";
        }
      }
    }
    leaf prefix-export-limit {
      type uint32 {
        range "0 .. 4294967295";
      }
      description "Maximum number of prefixes that can be exported";
    }
    container rib-groups {
      description "Routing table groups for importing OSPF routes";
      leaf inet {
        type string;
        description "Name of the IPv4/v6 routing table group";
      }
      leaf inet3 {
        type string;
        description "Name of the IPv4/v6 inet.3 routing table group";
      }
    }
    leaf job-stats {
      type empty;
      description "Collect job statistics";
    }
    container overload {
      description "Set the overload mode (repel transit traffic)";
      presence "enable overload";
      leaf timeout {
        type uint32 {
          range "60 .. 3600";
        }
        description "Time after which overload mode is reset";
        units seconds;
      }
      leaf allow-route-leaking {
        type empty;
        description "Allow routes to be leaked when overload is configured";
      }
      leaf stub-network {
        type empty;
        description "Advertise Stub Network with maximum metric";
      }
      leaf intra-area-prefix {
        type empty;
        description "Advertise Intra Area Prefix with maximum metric";
      }
      leaf as-external {
        type empty;
        description "Advertise As External with maximum usable metric";
      }
    }
    container database-protection {
      description "Configure database protection attributes";
      presence "enable database-protection";
      leaf maximum-lsa {
        type uint32 {
          range "1 .. 1000000";
        }
        description "Maximum allowed non self-generated LSAs";
      }
      leaf warning-only {
        type empty;
        description "Emit only a warning when LSA maximum limit is exceeded";
      }
      leaf warning-threshold {
        type uint8 {
          range "30 .. 100";
        }
        description "Percentage of LSA maximum above which to trigger warning";
        units percent;
      }
      leaf ignore-count {
        type uint8 {
          range "1 .. 32";
        }
        description "Maximum number of times to go into ignore state";
      }
      leaf ignore-time {
        type uint16 {
          range "30 .. 3600";
        }
        description "Time to stay in ignore state and ignore all neighbors";
        units seconds;
      }
      leaf reset-time {
        type uint32 {
          range "60 .. 86400";
        }
        description "Time after which the ignore count gets reset to zero";
        units seconds;
      }
    }
    container graceful-restart {
      description "Configure graceful restart attributes";
      choice enable-disable {
        case case_1 {
          leaf disable {
            type empty;
            description "Disable OSPF graceful restart capability";
          }
        }
      }
      leaf restart-duration {
        type uint32 {
          range "1 .. 3600";
        }
        description "Time for all neighbors to become full";
        units seconds;
      }
      leaf notify-duration {
        type uint32 {
          range "1 .. 3600";
        }
        description "Time to send all max-aged grace LSAs";
        units seconds;
      }
      container helper-disable {
        description "Disable graceful restart helper capability";
        presence "enable helper-disable";
        choice disable-choices {
          case case_1 {
            leaf standard {
              type empty;
              description "Disable helper-mode for rfc3623 based GR";
            }
          }
          case case_2 {
            leaf restart-signaling {
              type empty;
              description "Disable helper mode for restart-signaling ";
            }
          }
          case case_3 {
            leaf both {
              type empty;
              description "Disable helper mode for both the types of GR";
            }
          }
        }
      }
      leaf no-strict-lsa-checking {
        type empty;
        description "Do not abort graceful helper mode upon LSA changes";
      }
    }
    leaf route-type-community {
      type enumeration {
        enum iana {
          description "BGP extended community value used is 0x0306";
        }
        enum vendor {
          description "Vendor BGP extended community value used is 0x8000";
        }
      }
      description "Specify BGP extended community value to encode OSPF route type";
    }
    container domain-id {
      description "Configure domain ID";
      choice domain_id_or_disable {
        case case_1 {
          leaf domain-id {
            type string;
            description "Domain ID";
          }
        }
        case case_2 {
          leaf disable {
            type empty;
            description "Disable domain ID";
          }
        }
      }
    }
    choice domain_vpn_tag_or_disable {
      case case_1 {
        leaf domain-vpn-tag {
          type uint32 {
            range "0 .. 4294967295";
          }
          description "Domain VPN tag for external LSA";
        }
      }
      case case_2 {
        leaf no-domain-vpn-tag {
          type empty;
          description "Disable domain VPN tag";
        }
      }
    }
    leaf preference {
      type uint32;
      description "Preference of internal routes";
    }
    leaf external-preference {
      type uint32;
      description "Preference of external routes";
    }
    leaf labeled-preference {
      type uint32;
      description "Preference of labeled routes";
    }
    leaf-list export {
      type "jt:policy-algebra";
      description "Export policy";
      ordered-by user;
    }
    leaf-list import {
      type "jt:policy-algebra";
      description "Import policy (for external routes or setting priority)";
      ordered-by user;
    }
    leaf reference-bandwidth {
      type string;
      description "Bandwidth for calculating metric defaults";
    }
    leaf lsa-refresh-interval {
      type uint32 {
        range "25 .. 50";
      }
      default "50";
      description "LSA refresh interval (minutes)";
    }
    leaf spf-delay {
      type uint32 {
        range "50 .. 8000";
      }
      description "Time to wait before running an SPF";
      status deprecated;
      units milliseconds;
    }
    leaf no-rfc-1583 {
      type empty;
      description "Disable RFC1583 compatibility";
    }
    leaf forwarding-address-to-broadcast {
      type empty;
      description "Set forwarding address in Type 5 LSA in broadcast network";
    }
    choice nssa-abr-option {
      case case_1 {
        leaf no-nssa-abr {
          type empty;
          description "Disable full NSSA functionality at ABR";
        }
      }
    }
    container sham-link {
      description "Configure parameters for sham links";
      presence "enable sham-link";
      leaf local {
        type "jt:ipaddr";
        description "Local sham link endpoint address";
      }
      leaf no-advertise-local {
        type empty;
        description "Don't advertise local sham link endpoint as stub in router LSA";
        status deprecated;
      }
    }
  }
  grouping juniper-protocols-pgm {
    container traceoptions {
      description "PGM trace options";
      list flag {
        description "Tracing parameters";
        key name;
        ordered-by user;
        leaf name {
          type enumeration {
            enum init {
              description "Trace initialization events";
            }
            enum show {
              description "Trace show command servicing";
            }
            enum route-socket {
              description "Trace route-socket events";
            }
            enum parse {
              description "Trace parser processing";
            }
            enum state {
              description "Trace state transitions";
            }
            enum packets {
              description "Trace packet processing";
            }
            enum all {
              description "Trace everything";
            }
          }
        }
        leaf send {
          type empty;
          description "Trace transmitted packets";
        }
        leaf receive {
          type empty;
          description "Trace received packets";
        }
        leaf detail {
          type empty;
          description "Trace detailed information";
        }
        leaf disable {
          type empty;
          description "Disable this trace flag";
        }
      }
    }
  }
  grouping juniper-protocols-pim {
    leaf protocol-instance-name {
      type string;
      description "Name of protocol instance under routing instance";
    }
    container family {
      description "Local address family";
      container any {
        description "Default properties for all address families";
        presence "enable any";
        leaf disable {
          type empty;
          description "Disable all families";
        }
      }
      container inet {
        description "IPv4 specific properties";
        presence "enable inet";
        choice enable-disable {
          case case_1 {
            leaf disable {
              type empty;
              description "Disable PIMv4 on all interfaces";
            }
          }
        }
      }
      container inet6 {
        description "IPv6 specific properties";
        presence "enable inet6";
        choice enable-disable {
          case case_1 {
            leaf disable {
              type empty;
              description "Disable PIMv6 on all interfaces";
            }
          }
        }
      }
    }
    choice enable-disable {
      case case_1 {
        leaf disable {
          type empty;
          description "Disable PIM";
        }
      }
    }
    container nonstop-routing {
      description "Configure PIM nonstop-routing attributes";
      choice enable-disable {
        case case_1 {
          leaf disable {
            type empty;
            description "Disable non-stop routing for PIM";
          }
        }
      }
    }
    container traceoptions {
      description "Trace options for PIM";
      container file {
        description "Trace file options";
        leaf filename {
          type string {
            length "1 .. 1024";
          }
          description "Name of file in which to write trace information";
        }
        leaf replace {
          type empty;
          description "Replace trace file rather than appending to it";
          status deprecated;
        }
        leaf size {
          type string;
          description "Maximum trace file size";
        }
        leaf files {
          type uint32 {
            range "2 .. 1000";
          }
          default "10";
          description "Maximum number of trace files";
        }
        leaf no-stamp {
          type empty;
          description "Do not timestamp trace file";
          status deprecated;
        }
        choice world-readable-choice {
          leaf world-readable {
            type empty;
            description "Allow any user to read the log file";
          }
          leaf no-world-readable {
            type empty;
            description "Don't allow any user to read the log file";
          }
        }
      }
      list flag {
        description "Tracing parameters";
        key name;
        ordered-by user;
        leaf name {
          type enumeration {
            enum route {
              description "Trace routing information";
            }
            enum packets {
              description "Trace all PIM packets";
            }
            enum hello {
              description "Trace hello packets";
            }
            enum register {
              description "Trace register/register-stop messages";
            }
            enum join {
              description "Trace join/prune/graft/graft-ack messages";
            }
            enum prune {
              description "Trace join/prune/graft/graft-ack messages";
            }
            enum graft {
              description "Trace join/prune/graft/graft-ack messages";
            }
            enum bootstrap {
              description "Trace bootstrap/RP/auto-RP messages";
            }
            enum rp {
              description "Trace bootstrap/RP/auto-RP messages";
            }
            enum autorp {
              description "Trace bootstrap/RP/auto-RP messages";
            }
            enum assert {
              description "Trace assert messages";
            }
            enum mdt {
              description "Trace messages related to multicast data tunnels";
            }
            enum nsr-synchronization {
              description "Trace NSR synchronization events";
            }
            enum bidirectional-df-election {
              description "Trace bidirectional PIM DF election events";
            }
            enum mofrr {
              description "Trace Multicast only Fast Re-Route messages";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
        leaf send {
          type empty;
          description "Trace transmitted packets";
        }
        leaf receive {
          type empty;
          description "Trace received packets";
        }
        leaf detail {
          type empty;
          description "Trace detailed information";
        }
        leaf disable {
          type empty;
          description "Disable this trace flag";
        }
        container filter {
          description "Filter to apply to this flag";
          presence "enable filter";
          uses pim_filter_obj;
        }
      }
    }
    container dense-groups {
      description "Dense mode groups for sparse-dense mode";
      leaf dynamic-reject {
        type empty;
        description "Reject dynamic autorp negative dense-mode prefixes learnt from network";
      }
      list pim-dense-group-type {
        key name;
        ordered-by user;
        leaf name {
          type "jt:ipprefix";
          description "Group address or range to forward in dense mode";
        }
        choice dense-group-flags {
          case case_1 {
            leaf reject {
              type empty;
              description "Do not include prefix as dense mode; force sparse mode";
            }
          }
          case case_2 {
            leaf announce {
              type empty;
              description "Advertise as negative prefix in auto-RP announce messages";
            }
          }
        }
      }
    }
    leaf vpn-tunnel-source {
      type "jt:ipv4addr";
      description "Source address for the provider space mGRE tunnel";
      status deprecated;
    }
    leaf vpn-group-address {
      type "jt:ipv4addr";
      description "Group address for the VPN in provider space";
      status deprecated;
    }
    leaf-list tunnel-devices {
      type "jt:interface-device";
      description "Tunnel devices to be used for creating mt interfaces";
      ordered-by user;
    }
    container rpf-selection {
      description "Select RPF neighbor";
      list group {
        description "IP prefix of multicast group";
        key name;
        ordered-by user;
        leaf name {
          type "jt:ipprefix";
          description "IP prefix of group";
        }
        container wildcard-source {
          description "Select RPF for (*,g) and unspecified (s,g) joins";
          presence "enable wildcard-source";
          leaf next-hop {
            type "jt:ipaddr";
            description "Next-hop address";
          }
        }
        list source {
          description "IP prefix of one or more multicast sources";
          key name;
          ordered-by user;
          leaf name {
            type "jt:ipprefix";
            description "IP prefix of source";
          }
          leaf next-hop {
            type "jt:ipaddr";
            description "Next-hop address";
          }
        }
      }
      list prefix-list {
        description "Multicast group prefix list";
        key name;
        ordered-by user;
        leaf name {
          type string;
          description "Name of prefix list to match against";
        }
        container wildcard-source {
          description "Select RPF for (*,g) and unspecified (s,g) joins";
          presence "enable wildcard-source";
          leaf next-hop {
            type "jt:ipaddr";
            description "Next-hop address";
          }
        }
        list source {
          description "IP prefix of one or more multicast sources";
          key name;
          ordered-by user;
          leaf name {
            type "jt:ipprefix";
            description "IP prefix of source";
          }
          leaf next-hop {
            type "jt:ipaddr";
            description "Next-hop address";
          }
        }
      }
    }
    container mvpn {
      description "PIM MVPN control-plane options";
      presence "enable mvpn";
      container autodiscovery {
        description "PE router autodiscovery options for SSM MDTs";
        status deprecated;
        leaf inet-mdt {
          type empty;
          description "MDT-SAFI PE autodiscovery for SSM MDTs";
        }
      }
      container family {
        description "PIM MVPN address family";
        container inet {
          description "IPv4 PIM MVPN specific properties";
          leaf rosen-mvpn {
            type empty;
            status deprecated;
          }
          leaf ngen-mvpn {
            type empty;
            status deprecated;
          }
          container autodiscovery {
            description "PE router autodiscovery options for SSM MDTs";
            leaf inet-mdt {
              type empty;
              description "MDT-SAFI PE autodiscovery for SSM MDTs";
            }
          }
          leaf disable {
            type empty;
            description "Disable family IPv4";
          }
        }
        container inet6 {
          description "IPv6 PIM MVPN specific properties";
          leaf rosen-mvpn {
            type empty;
            status deprecated;
          }
          leaf ngen-mvpn {
            type empty;
            status deprecated;
          }
          container autodiscovery {
            description "PE router autodiscovery options for SSM MDTs";
            leaf inet-mdt {
              type empty;
              description "MDT-SAFI PE autodiscovery for SSM MDTs";
            }
          }
          leaf disable {
            type empty;
            description "Disable family IPv6";
          }
        }
      }
    }
    container rib-group {
      description "Routing table group";
      uses rib_group_type;
    }
    leaf-list import {
      type "jt:policy-algebra";
      description "PIM sparse import join policy";
      ordered-by user;
    }
    leaf-list export {
      type "jt:policy-algebra";
      description "PIM sparse export join policy";
      ordered-by user;
    }
    container mldp-inband-signalling {
      presence "enable mldp-inband-signalling";
      leaf-list policy {
        type "jt:policy-algebra";
        description "PIM MLDP join translation filter policy";
        ordered-by user;
      }
    }
    container rpf-vector {
      description "RPF vector TLV";
      leaf-list policy {
        type "jt:policy-algebra";
        description "RPF vector TLV include policy";
        ordered-by user;
      }
    }
    leaf assert-timeout {
      type uint32 {
        range "5 .. 210";
      }
      default "180";
      description "Set assert timeout";
    }
    leaf assert-robust-count {
      type uint32 {
        range "1 .. 5";
      }
      default "2";
      description "Number of assert messages an assert winner sends in one cycle";
    }
    leaf join-prune-timeout {
      type uint32 {
        range "210 .. 420";
      }
      default "210";
      description "Set join/prune timeout";
    }
    container spt-threshold {
      description "Set shortest-path-tree threshold policy";
      leaf-list infinity {
        type "jt:policy-algebra";
        description "Apply policy to always remain on shared tree";
        ordered-by user;
      }
    }
    container sglimit {
      description "Set limit on number of (S,G) states ";
      list family {
        description "Protocol family";
        key name;
        ordered-by user;
        leaf name {
          type enumeration {
            enum inet {
              description "IPv4 family";
            }
            enum inet6 {
              description "IPv6 family";
            }
          }
        }
        leaf maximum {
          type uint32 {
            range "1 .. 65535";
          }
          description "Maximum limit above which additional entries are not accepted";
        }
        leaf threshold {
          type uint32 {
            range "1 .. 100";
          }
          description "Percentage of maximum at which to start generating warnings";
        }
        leaf log-interval {
          type uint32 {
            range "1 .. 65535";
          }
          description "Time between successive log messages";
        }
      }
      leaf maximum {
        type uint32 {
          range "1 .. 65535";
        }
        description "Maximum limit above which additional entries are not accepted";
      }
      leaf threshold {
        type uint32 {
          range "1 .. 100";
        }
        description "Percentage of maximum at which to start generating warnings";
      }
      leaf log-interval {
        type uint32 {
          range "1 .. 65535";
        }
        description "Time between successive log messages";
      }
    }
    container rp {
      description "Router's rendezvous point properties";
      leaf bootstrap-priority {
        type uint32 {
          range "0 .. 255";
        }
        description "Eligibility to be the bootstrap router (IPv4 only)";
      }
      leaf-list bootstrap-import {
        type "jt:policy-algebra";
        description "Bootstrap import policy (IPv4 only)";
        ordered-by user;
      }
      leaf-list bootstrap-export {
        type "jt:policy-algebra";
        description "Bootstrap export policy (IPv4 only)";
        ordered-by user;
      }
      container bootstrap {
        description "Bootstrap properties";
        container family {
          description "Bootstrap address family";
          container inet {
            description "IPv4 bootstrap properties";
            uses pim_bootstrap_options_type;
          }
          container inet6 {
            description "IPv6 bootstrap properties";
            uses pim_bootstrap_options_type;
          }
        }
      }
      container register-limit {
        description "Set limit on incoming registers that create (S,G) state";
        list family {
          description "Protocol family";
          key name;
          ordered-by user;
          leaf name {
            type enumeration {
              enum inet {
                description "IPv4 family";
              }
              enum inet6 {
                description "IPv6 family";
              }
            }
          }
          leaf maximum {
            type uint32 {
              range "1 .. 65535";
            }
            description "Maximum limit above which additional entries are not accepted";
          }
          leaf threshold {
            type uint32 {
              range "1 .. 100";
            }
            description "Percentage of maximum at which to start generating warnings";
          }
          leaf log-interval {
            type uint32 {
              range "1 .. 65535";
            }
            description "Time between successive log messages";
          }
        }
        leaf maximum {
          type uint32 {
            range "1 .. 65535";
          }
          description "Maximum limit above which additional entries are not accepted";
        }
        leaf threshold {
          type uint32 {
            range "1 .. 100";
          }
          description "Percentage of maximum at which to start generating warnings";
        }
        leaf log-interval {
          type uint32 {
            range "1 .. 65535";
          }
          description "Time between successive log messages";
        }
      }
      container group-rp-mapping {
        description "Group-rp-mapping";
        list family {
          description "Protocol family";
          key name;
          ordered-by user;
          leaf name {
            type enumeration {
              enum inet {
                description "IPv4 family";
              }
              enum inet6 {
                description "IPv6 family";
              }
            }
          }
          leaf maximum {
            type uint32 {
              range "1 .. 65535";
            }
            description "Maximum limit above which additional entries are not accepted";
          }
          leaf threshold {
            type uint32 {
              range "1 .. 100";
            }
            description "Percentage of maximum at which to start generating warnings";
          }
          leaf log-interval {
            type uint32 {
              range "1 .. 65535";
            }
            description "Time between successive log messages";
          }
        }
        leaf maximum {
          type uint32 {
            range "1 .. 65535";
          }
          description "Maximum limit above which additional entries are not accepted";
        }
        leaf threshold {
          type uint32 {
            range "1 .. 100";
          }
          description "Percentage of maximum at which to start generating warnings";
        }
        leaf log-interval {
          type uint32 {
            range "1 .. 65535";
          }
          description "Time between successive log messages";
        }
      }
      leaf-list rp-register-policy {
        type "jt:policy-algebra";
        description "RP policy applied to incoming register messages";
        ordered-by user;
      }
      leaf-list dr-register-policy {
        type "jt:policy-algebra";
        description "DR policy applied to outgoing register messages";
        ordered-by user;
      }
      container local {
        description "Router's local RP properties";
        leaf address {
          type "jt:ipv4addr";
          description "Local RP address (IPv4 only)";
        }
        choice enable-disable {
          case case_1 {
            leaf disable {
              type empty;
              description "Disable this RP (IPv4 only)";
            }
          }
        }
        leaf priority {
          type uint32 {
            range "0 .. 255";
          }
          description "Router's priority for becoming an RP (IPv4 only)";
        }
        leaf hold-time {
          type uint32 {
            range "1 .. 65535";
          }
          description "How long neighbor considers this router to be up, in seconds (IPv4 only)";
        }
        list group-ranges {
          description "Group address range for which this router can be an RP (IPv4 only)";
          key name;
          ordered-by user;
          leaf name {
            type "jt:ipv4prefix";
          }
        }
        leaf override {
          type empty;
          description "Static RP mapping will take precedence over dynamic";
        }
        container family {
          description "Local RP address family";
          container inet {
            description "IPv4 local RP properties";
            leaf address {
              type "jt:ipv4addr";
              description "Local RP address";
            }
            choice enable-disable {
              case case_1 {
                leaf disable {
                  type empty;
                  description "Disable this RP";
                }
              }
            }
            leaf priority {
              type uint32 {
                range "0 .. 255";
              }
              description "Router's priority for becoming an RP";
            }
            leaf hold-time {
              type uint32 {
                range "1 .. 65535";
              }
              description "How long neighbor considers this router to be up, in seconds";
            }
            list group-ranges {
              description "Group address range for which this router can be an RP";
              key name;
              ordered-by user;
              leaf name {
                type "jt:ipv4prefix";
              }
            }
            leaf override {
              type empty;
              description "Static RP mapping will take precedence over dynamic";
            }
            container anycast-pim {
              description "Attributes for IPv4 anycast PIM";
              container rp-set {
                description "Rendezvous points belonging to anycast RP set";
                list address {
                  description "IPv4 address of one or more remote anycast RPs";
                  key name;
                  ordered-by user;
                  leaf name {
                    type "jt:ipaddr";
                    description "IPv4 address of remote anycast RP";
                  }
                  leaf forward-msdp-sa {
                    type empty;
                    description "Forward SAs learned from MSDP to this RP";
                  }
                }
              }
              leaf local-address {
                type "jt:ipaddr";
                description "Local address for replicating register messages to other RPs";
              }
            }
          }
          container inet6 {
            description "IPv6 local RP properties";
            leaf address {
              type "jt:ipv6addr";
              description "Local RP address";
            }
            choice enable-disable {
              case case_1 {
                leaf disable {
                  type empty;
                  description "Disable this RP";
                }
              }
            }
            leaf priority {
              type uint32 {
                range "0 .. 255";
              }
              description "Router's priority for becoming an RP";
            }
            leaf hold-time {
              type uint32 {
                range "1 .. 65535";
              }
              description "How long neighbor considers this router to be up, in seconds";
            }
            list group-ranges {
              description "Group address range for which this router can be an RP";
              key name;
              ordered-by user;
              leaf name {
                type "jt:ipv6prefix";
              }
            }
            leaf override {
              type empty;
              description "Static RP mapping will take precedence over dynamic";
            }
            container anycast-pim {
              description "Attributes for IPv6 anycast PIM";
              container rp-set {
                description "Rendezvous points belonging to anycast RP set";
                list address {
                  description "IPv6 address of one or more remote anycast RPs";
                  key name;
                  ordered-by user;
                  leaf name {
                    type "jt:ipv6addr";
                    description "IPv6 address of remote anycast RP";
                  }
                }
              }
              leaf local-address {
                type "jt:ipv6addr";
                description "Local address for replicating register messages to other RPs";
              }
            }
          }
        }
      }
      container embedded-rp {
        description "Set embedded-RP mode (IPv6 only)";
        presence "enable embedded-rp";
        list group-ranges {
          description "Group address range of RP";
          key name;
          ordered-by user;
          uses pim_rp_group_range_type;
        }
        leaf maximum-rps {
          type uint32 {
            range "1 .. 500";
          }
          default "100";
          description "Maximum number of embedded RPs";
        }
      }
      container auto-rp {
        description "Set auto-RP mode (IPv4 only)";
        choice autorp-mode {
          case case_1 {
            leaf discovery {
              type empty;
              description "Listen for auto-RP discovery messages";
            }
          }
          case case_2 {
            leaf announce {
              type empty;
              description "Transmit auto-RP announcement messages";
            }
          }
          case case_3 {
            leaf mapping {
              type empty;
              description "Transmit auto-RP mapping messages";
            }
          }
        }
        choice mapping-agent-election-choice {
          leaf mapping-agent-election {
            type empty;
            description "Consider higher-addressed mapping agents as authoritative";
          }
          leaf no-mapping-agent-election {
            type empty;
            description "Don't consider higher-addressed mapping agents as authoritative";
          }
        }
      }
      container static {
        description "Configure static PIM RPs";
        list address {
          description "RP address";
          key name;
          ordered-by user;
          leaf name {
            type "jt:ipaddr";
            description "IP address of RP";
          }
          leaf version {
            type uint32 {
              range "1 .. 2";
            }
            description "PIM version of RP";
            status deprecated;
          }
          list group-ranges {
            description "Group address range of RP";
            key name;
            ordered-by user;
            uses pim_rp_group_range_type;
          }
          leaf override {
            type empty;
            description "Static RP mapping will take precedence over dynamic";
          }
        }
      }
      container bidirectional {
        description "Configure PIM bidirectional-mode RPs";
        list address {
          description "RP address";
          key name;
          ordered-by user;
          leaf name {
            type "jt:ipaddr";
            description "IP address of RP";
          }
          leaf priority {
            type uint32 {
              range "0 .. 255";
            }
            description "Router's priority for becoming an RP";
          }
          leaf hold-time {
            type uint32 {
              range "1 .. 65535";
            }
            description "How long neighbor considers this router to be up";
            units seconds;
          }
          list group-ranges {
            description "Group address range of RP";
            key name;
            ordered-by user;
            uses pim_rp_group_range_type;
          }
        }
      }
    }
    leaf passive {
      type empty;
      description "Configure PIM protocol in passive mode";
    }
    list interface {
      description "PIM interface options";
      key name;
      ordered-by user;
      leaf name {
        type string;
        description "Interface name";
      }
      container family {
        description "Local address family";
        container any {
          description "Default properties for all families";
          presence "enable any";
          leaf disable {
            type empty;
            description "Disable all families";
          }
        }
        container inet {
          description "IPv4 specific properties";
          presence "enable inet";
          container bfd-liveness-detection {
            description "Bidirectional Forwarding Detection options";
            leaf version {
              type enumeration {
                enum 0 {
                  description "BFD version 0 (deprecated)";
                }
                enum 1 {
                  description "BFD version 1";
                }
                enum automatic {
                  description "Choose BFD version automatically";
                }
              }
              default "automatic";
              description "BFD protocol version number";
            }
            leaf minimum-interval {
              type uint32 {
                range "1 .. 255000";
              }
              description "Minimum transmit and receive interval";
              units milliseconds;
            }
            leaf minimum-transmit-interval {
              type uint32 {
                range "1 .. 255000";
              }
              description "Minimum transmit interval";
              status deprecated;
              units milliseconds;
            }
            leaf minimum-receive-interval {
              type uint32 {
                range "1 .. 255000";
              }
              description "Minimum receive interval";
              units milliseconds;
            }
            leaf multiplier {
              type uint32 {
                range "1 .. 255";
              }
              default "3";
              description "Detection time multiplier";
            }
            leaf inline-disable {
              type empty;
              description "Disable inline mode for this BFD session";
            }
            leaf pdu-size {
              type uint32 {
                range "24 .. 9000";
              }
              default "24";
              description "BFD transport protocol payload size";
            }
            choice adaptation-choice {
              case case_1 {
                leaf no-adaptation {
                  type empty;
                  description "Disable adaptation";
                }
              }
            }
            container transmit-interval {
              description "Transmit-interval options";
              leaf minimum-interval {
                type uint32 {
                  range "1 .. 255000";
                }
                description "Minimum transmit interval";
                units milliseconds;
              }
              leaf threshold {
                type uint32;
                description "High transmit interval triggering a trap";
                units milliseconds;
              }
            }
            container detection-time {
              description "Detection-time options";
              leaf threshold {
                type uint32;
                description "High detection-time triggering a trap";
                units milliseconds;
              }
            }
            container authentication {
              description "Authentication options";
              leaf key-chain {
                type string;
                description "Key chain name";
              }
              leaf algorithm {
                type enumeration {
                  enum simple-password {
                    description "Simple password";
                  }
                  enum keyed-md5 {
                    description "Keyed message Digest 5";
                  }
                  enum meticulous-keyed-md5 {
                    description "Meticulous keyed message Digest 5";
                  }
                  enum keyed-sha-1 {
                    description "Keyed secure hash algorithm (SHA1) ";
                  }
                  enum meticulous-keyed-sha-1 {
                    description "Meticulous keyed secure hash algorithm (SHA1) ";
                  }
                }
                description "Algorithm name";
              }
              leaf loose-check {
                type empty;
                description "Verify authentication only if authentication is negotiated";
              }
            }
          }
          leaf mcae-mac-synchronize {
            type empty;
            description "Mclag mac synchronization";
          }
          choice enable-disable {
            case case_1 {
              leaf disable {
                type empty;
                description "Disable PIMv4 on this interface";
              }
            }
          }
        }
        container inet6 {
          description "IPv6 specific properties";
          presence "enable inet6";
          container bfd-liveness-detection {
            description "Bidirectional Forwarding Detection options";
            leaf version {
              type enumeration {
                enum 0 {
                  description "BFD version 0 (deprecated)";
                }
                enum 1 {
                  description "BFD version 1";
                }
                enum automatic {
                  description "Choose BFD version automatically";
                }
              }
              default "automatic";
              description "BFD protocol version number";
            }
            leaf minimum-interval {
              type uint32 {
                range "1 .. 255000";
              }
              description "Minimum transmit and receive interval";
              units milliseconds;
            }
            leaf minimum-transmit-interval {
              type uint32 {
                range "1 .. 255000";
              }
              description "Minimum transmit interval";
              status deprecated;
              units milliseconds;
            }
            leaf minimum-receive-interval {
              type uint32 {
                range "1 .. 255000";
              }
              description "Minimum receive interval";
              units milliseconds;
            }
            leaf multiplier {
              type uint32 {
                range "1 .. 255";
              }
              default "3";
              description "Detection time multiplier";
            }
            leaf inline-disable {
              type empty;
              description "Disable inline mode for this BFD session";
            }
            leaf pdu-size {
              type uint32 {
                range "24 .. 9000";
              }
              default "24";
              description "BFD transport protocol payload size";
            }
            choice adaptation-choice {
              case case_1 {
                leaf no-adaptation {
                  type empty;
                  description "Disable adaptation";
                }
              }
            }
            container transmit-interval {
              description "Transmit-interval options";
              leaf minimum-interval {
                type uint32 {
                  range "1 .. 255000";
                }
                description "Minimum transmit interval";
                units milliseconds;
              }
              leaf threshold {
                type uint32;
                description "High transmit interval triggering a trap";
                units milliseconds;
              }
            }
            container detection-time {
              description "Detection-time options";
              leaf threshold {
                type uint32;
                description "High detection-time triggering a trap";
                units milliseconds;
              }
            }
            container authentication {
              description "Authentication options";
              leaf key-chain {
                type string;
                description "Key chain name";
              }
              leaf algorithm {
                type enumeration {
                  enum simple-password {
                    description "Simple password";
                  }
                  enum keyed-md5 {
                    description "Keyed message Digest 5";
                  }
                  enum meticulous-keyed-md5 {
                    description "Meticulous keyed message Digest 5";
                  }
                  enum keyed-sha-1 {
                    description "Keyed secure hash algorithm (SHA1) ";
                  }
                  enum meticulous-keyed-sha-1 {
                    description "Meticulous keyed secure hash algorithm (SHA1) ";
                  }
                }
                description "Algorithm name";
              }
              leaf loose-check {
                type empty;
                description "Verify authentication only if authentication is negotiated";
              }
            }
          }
          choice enable-disable {
            case case_1 {
              leaf disable {
                type empty;
                description "Disable PIMv6 on this interface";
              }
            }
          }
        }
      }
      choice enable-disable {
        case case_1 {
          leaf disable {
            type empty;
            description "Disable PIM on this interface";
          }
        }
      }
      container bidirectional {
        description "PIM bidirectional mode properties";
        container df-election {
          description "Bidir designated forwarder properties";
          leaf robustness-count {
            type uint32 {
              range "1 .. 10";
            }
            description "Election robustness count";
          }
          leaf offer-period {
            type uint32 {
              range "100 .. 10000";
            }
            description "Election offer message period";
            units milliseconds;
          }
          leaf backoff-period {
            type uint32 {
              range "100 .. 65535";
            }
            description "Election backoff period";
            units milliseconds;
          }
        }
      }
      leaf mode {
        type enumeration {
          enum dense {
            description "Dense mode";
          }
          enum sparse {
            description "Sparse mode";
          }
          enum sparse-dense {
            description "Sparse-dense mode";
          }
          enum bidirectional-sparse {
            description "Bidirectional-sparse mode";
          }
          enum bidirectional-sparse-dense {
            description "Bidirectional-sparse-dense mode";
          }
        }
        description "Mode of interface";
      }
      leaf priority {
        type uint32 {
          range "0 .. 4294967295";
        }
        description "Hello option DR priority";
      }
      container stickydr {
        description "Make DR sticky";
        presence "enable stickydr";
      }
      container multiple-triggered-joins {
        description "Send multiple pim triggered joins in quick intervals";
        presence "enable multiple-triggered-joins";
        leaf count {
          type uint16 {
            range "2 .. 15";
          }
          default "2";
          description "Set number of triggered joins to be sent";
        }
        leaf interval {
          type uint16 {
            range "100 .. 1000";
          }
          default "100";
          description "Set interval between multiple triggered joins to be sent in milliseconds";
        }
      }
      leaf version {
        type uint32 {
          range "1 .. 2";
        }
        description "Force PIM version";
        status deprecated;
      }
      leaf hello-interval {
        type uint32 {
          range "0 .. 255";
        }
        description "Hello interval";
        units seconds;
      }
      leaf-list neighbor-policy {
        type "jt:policy-algebra";
        description "PIM neighbor policy applied to incoming hello messages";
        ordered-by user;
      }
      leaf-list accept-join-always-from {
        type "jt:policy-algebra";
        description "Accept pim join/prune messages based on the policy configured";
        ordered-by user;
      }
      leaf accept-remote-source {
        type empty;
        description "Accept traffic from remote source";
      }
      container dual-dr {
        description "Configure PIM Dual DR";
        presence "enable dual-dr";
        leaf enhanced {
          type empty;
          description "Enable enhanced PIM Dual DR";
        }
      }
      leaf distributed-dr {
        type empty;
        description "PIM Distributed DR";
      }
      leaf reset-tracking-bit {
        type empty;
        description "Clear tracking-bit in PIM Hello LAN Prune Delay Option";
      }
      leaf propagation-delay {
        type uint32 {
          range "250 .. 2000";
        }
        default "500";
        description "Propagation delay value";
        units milliseconds;
      }
      leaf override-interval {
        type uint32 {
          range "500 .. 6000";
        }
        default "2000";
        description "Override interval value";
        units milliseconds;
      }
      leaf disable-packet-register {
        type empty;
        description "Disable PIM packet registers on first hop router";
      }
      container bfd-liveness-detection {
        description "Bidirectional Forwarding Detection options (ipv4 only)";
        status deprecated;
        leaf version {
          type enumeration {
            enum 0 {
              description "BFD version 0 (deprecated)";
            }
            enum 1 {
              description "BFD version 1";
            }
            enum automatic {
              description "Choose BFD version automatically";
            }
          }
          default "automatic";
          description "BFD protocol version number";
        }
        leaf minimum-interval {
          type uint32 {
            range "1 .. 255000";
          }
          description "Minimum transmit and receive interval";
          units milliseconds;
        }
        leaf minimum-transmit-interval {
          type uint32 {
            range "1 .. 255000";
          }
          description "Minimum transmit interval";
          status deprecated;
          units milliseconds;
        }
        leaf minimum-receive-interval {
          type uint32 {
            range "1 .. 255000";
          }
          description "Minimum receive interval";
          units milliseconds;
        }
        leaf multiplier {
          type uint32 {
            range "1 .. 255";
          }
          default "3";
          description "Detection time multiplier";
        }
        leaf inline-disable {
          type empty;
          description "Disable inline mode for this BFD session";
        }
        leaf pdu-size {
          type uint32 {
            range "24 .. 9000";
          }
          default "24";
          description "BFD transport protocol payload size";
        }
        choice adaptation-choice {
          case case_1 {
            leaf no-adaptation {
              type empty;
              description "Disable adaptation";
            }
          }
        }
        container transmit-interval {
          description "Transmit-interval options";
          leaf minimum-interval {
            type uint32 {
              range "1 .. 255000";
            }
            description "Minimum transmit interval";
            units milliseconds;
          }
          leaf threshold {
            type uint32;
            description "High transmit interval triggering a trap";
            units milliseconds;
          }
        }
        container detection-time {
          description "Detection-time options";
          leaf threshold {
            type uint32;
            description "High detection-time triggering a trap";
            units milliseconds;
          }
        }
        container authentication {
          description "Authentication options";
          leaf key-chain {
            type string;
            description "Key chain name";
          }
          leaf algorithm {
            type enumeration {
              enum simple-password {
                description "Simple password";
              }
              enum keyed-md5 {
                description "Keyed message Digest 5";
              }
              enum meticulous-keyed-md5 {
                description "Meticulous keyed message Digest 5";
              }
              enum keyed-sha-1 {
                description "Keyed secure hash algorithm (SHA1) ";
              }
              enum meticulous-keyed-sha-1 {
                description "Meticulous keyed secure hash algorithm (SHA1) ";
              }
            }
            description "Algorithm name";
          }
          leaf loose-check {
            type empty;
            description "Verify authentication only if authentication is negotiated";
          }
        }
      }
    }
    container mdt {
      description "Configure multicast data tunnel parameters";
      status deprecated;
      container threshold {
        description "Threshold for creation of multicast tunnels";
        list group {
          description "IP prefix of multicast group";
          key name;
          ordered-by user;
          leaf name {
            type "jt:ipprefix";
            description "IP prefix of group";
          }
          list source {
            description "IP prefix of one or more multicast sources ";
            key name;
            ordered-by user;
            leaf name {
              type "jt:ipprefix";
              description "IP prefix of source";
            }
            leaf rate {
              type uint32 {
                range "10 .. 1000000";
              }
              description "Data threshold to create new tunnel";
              units kilobits;
            }
          }
        }
      }
      leaf data-mdt-reuse {
        type empty;
        description "Allow multiple customer streams to be transmitted over one data tunnel ";
      }
      leaf tunnel-limit {
        type uint32 {
          range "0 .. 8192";
        }
        description "Maximum multicast data tunnels";
      }
      leaf group-range {
        type "jt:ipprefix";
        description "Group address range for multicast data tunnels";
      }
    }
    container graceful-restart {
      description "Configure graceful restart attributes";
      choice enable-disable {
        case case_1 {
          leaf disable {
            type empty;
            description "Disable PIM graceful restart capability";
          }
        }
      }
      leaf restart-duration {
        type uint32 {
          range "30 .. 300";
        }
        description "Maximum time for graceful restart to finish (seconds)";
        units seconds;
      }
      leaf no-bidirectional-mode {
        type empty;
        description "Disable PIM graceful restart for bidirectional mode";
      }
      leaf restart-complete-duration {
        type uint32 {
          range "5 .. 300";
        }
        description "Maximum time for graceful restart to complete (seconds)";
        units seconds;
      }
    }
    container join-load-balance {
      description "Configure PIM join load balancing";
      presence "enable join-load-balance";
      leaf automatic {
        type empty;
        description "Enable automatic PIM join load balancing";
      }
    }
    leaf standby-path-creation-delay {
      type uint32 {
        range "1 .. 300";
      }
      description "Amount of time to wait before creating standby path";
      units seconds;
    }
    leaf idle-standby-path-switchover-delay {
      type uint32 {
        range "1 .. 300";
      }
      description "Amount of time to wait before switching over to idle standby path";
      units seconds;
    }
    leaf dr-election-on-p2p {
      type empty;
      description "Enable DR election on Point-to-Point Interfaces";
    }
    leaf no-wildcard-register-stop {
      type empty;
      description "Disable sending of wildcard register stop message";
    }
    leaf nexthop-hold-time {
      type uint32 {
        range "1 .. 1000";
      }
      description "Nexthop hold time in milliseconds";
      units milliseconds;
    }
    leaf mpls-internet-multicast {
      type empty;
      description "Enable support for Internet Multicast over MPLS";
    }
    container join-make-before-break {
      description "Enable PIM Join Make-Before-Break during RPF neighbor change";
      choice enable-disable {
        case case_1 {
          leaf disable {
            type empty;
            description "Disable Make-Before-Break for PIM RPF neighbor change";
          }
        }
      }
    }
    leaf reset-tracking-bit {
      type empty;
      description "Clear tracking-bit in PIM Hello LAN Prune Delay Option";
    }
    leaf propagation-delay {
      type uint32 {
        range "250 .. 2000";
      }
      default "500";
      description "Propagation delay value";
      units milliseconds;
    }
    leaf override-interval {
      type uint32 {
        range "500 .. 6000";
      }
      default "2000";
      description "Override interval value";
      units milliseconds;
    }
    leaf disable-packet-register {
      type empty;
      description "Disable PIM packet registers on first hop router";
    }
    container default-vpn-source {
      description "Let all VRFs use master loopback address for mt interfaces";
      presence "enable default-vpn-source";
      leaf interface-name {
        type "jt:interface-unit";
        description "Master loopback interface name";
      }
    }
  }
  grouping juniper-protocols-protection-group {
    container ethernet-aps {
      description "Ethernet APS configuration";
      uses juniper-protocols-protection-group-eaps;
    }
    container traceoptions {
      description "Tracing options for debugging protocol operation";
      uses erp-trace-options;
    }
    leaf restore-interval {
      type uint32 {
        range "1 .. 12";
      }
      default "5";
      description "Wait to restore interval";
      units minutes;
    }
    leaf guard-interval {
      type uint32 {
        range "10 .. 2000";
      }
      default "500";
      description "Guard timer interval in 10ms steps";
      units milliseconds;
    }
    leaf hold-interval {
      type uint32 {
        range "0 .. 10000";
      }
      default "0";
      description "Hold off timer interval in 100ms steps";
      units milliseconds;
    }
    list ethernet-ring {
      description "Ethernet ring";
      key name;
      ordered-by user;
      uses juniper-protocols-protection-group-ethernet-ring;
    }
  }
  grouping erp-trace-options {
    description "Trace options for Ethernet Ring Protocol";
    list flag {
      description "Tracing parameters";
      key name;
      ordered-by user;
      leaf name {
        type enumeration {
          enum events {
            description "Trace events to the protocol state machine";
          }
          enum pdu {
            description "Trace R-APS PDU reception and transmission";
          }
          enum timers {
            description "Trace protocol timers";
          }
          enum state-machine {
            description "Trace R-APS state machine";
          }
          enum periodic-packet-management {
            description "Trace periodic packet management state and events";
          }
          enum config {
            description "Trace protocol configuration";
          }
          enum normal {
            description "Trace protocol general log messages";
          }
          enum debug {
            description "Trace protocol debug log messages";
          }
          enum all {
            description "Trace all";
          }
        }
      }
    }
    container file {
      description "Trace file options";
      leaf filename {
        type string {
          length "1 .. 1024";
        }
        description "Name of file in which to write trace information";
      }
      leaf replace {
        type empty;
        description "Replace trace file rather than appending to it";
        status deprecated;
      }
      leaf size {
        type string;
        description "Maximum trace file size";
      }
      leaf files {
        type uint32 {
          range "2 .. 1000";
        }
        default "10";
        description "Maximum number of trace files";
      }
      leaf no-stamp {
        type empty;
        description "Do not timestamp trace file";
        status deprecated;
      }
      choice world-readable-choice {
        leaf world-readable {
          type empty;
          description "Allow any user to read the log file";
        }
        leaf no-world-readable {
          type empty;
          description "Don't allow any user to read the log file";
        }
      }
    }
  }
  grouping juniper-protocols-protection-group-eaps {
    list profile {
      key name;
      uses juniper-protocols-protection-group-eaps-profile;
    }
  }
  grouping juniper-protocols-protection-group-eaps-profile {
    description "Ethernet APS profile";
    leaf name {
      type string {
        length "1 .. 32";
      }
      description "Profile name";
    }
    leaf protocol {
      type enumeration {
        enum ccm {
          description "Use CCM packets for protection.";
        }
        enum "G.8031" {
          description "Use G.8031 packets for protection.";
        }
      }
      description "Protocol value";
    }
    leaf revert-time {
      type uint32 {
        range "0 .. 15";
      }
      default "4";
      description "Reversion time in minutes, 0 would mean no reversion";
      units minutes;
    }
    leaf hold-time {
      type uint32 {
        range "0 .. 10000";
      }
      default "0";
      description "Hold time in seconds";
      units "milli seconds";
    }
    leaf local-request {
      type enumeration {
        enum lockout {
          description "Lockout protection";
        }
      }
      description "Local APS request";
    }
  }
  grouping juniper-protocols-protection-group-ethernet-ring {
    description "Ethernet Ring protection group configuration";
    leaf name {
      type string {
        length "1 .. 32";
      }
      description "Name of Ethernet Ring protection group";
    }
    leaf node-id {
      type "jt:mac-unicast";
      description "Node ID of the protection group, by default bridge's MAC";
    }
    leaf ring-protection-link-owner {
      type empty;
      description "Ring protection link owner flag, one ring should have only one node as a ring protection link owner";
    }
    leaf level {
      type uint32 {
        range "0 .. 7";
      }
      description "MPG Level value for R-APS PDU";
    }
    leaf restore-interval {
      type uint32 {
        range "1 .. 12";
      }
      description "Wait to restore interval";
      units minutes;
    }
    leaf guard-interval {
      type uint32 {
        range "10 .. 2000";
      }
      description "Guard timer interval in 10ms";
      units milliseconds;
    }
    leaf hold-interval {
      type uint32 {
        range "0 .. 10000";
      }
      description "Hold off timer interval in 100ms steps";
      units milliseconds;
    }
    leaf non-revertive {
      type empty;
      description "Non-revertive mode of operation";
    }
    leaf wait-to-block-interval {
      type uint32 {
        range "5 .. 10";
      }
      default "5";
      description "Wait to block interval";
      units seconds;
    }
    leaf major-ring-name {
      type string {
        length "1 .. 32";
      }
      description "Name of major-ring to which this sub-ring node attached";
    }
    leaf propagate-tc {
      type empty;
      description "Enable Topology Change Propagation to major-ring from the sub-ring";
    }
    leaf compatibility-version {
      type uint32 {
        range "1 .. 2";
      }
      default "2";
      description "G.8032 compatibility version";
    }
    leaf ring-id {
      type uint32 {
        range "1 .. 239";
      }
      default "1";
      description "Ethernet Ring ID of protection group";
    }
    leaf non-vc-mode {
      type empty;
      description "Node is operating in non virtual channel mode";
    }
    leaf dot1p-priority {
      type uint32 {
        range "0 .. 7";
      }
      default "0";
      description "IEEE 802.1p priority of transmitted R-APS";
    }
    container east-interface {
      description "East interface configuration";
      presence "enable east-interface";
      uses erp-interface;
    }
    container west-interface {
      description "West interface configuration";
      presence "enable west-interface";
      uses erp-interface;
    }
    leaf control-vlan {
      type string;
      description "Dedicated VLAN identifier - VLAN id or VLAN name";
    }
    container data-channel {
      description "Ring instance data channel";
      presence "enable data-channel";
      uses erp-data-channel;
    }
  }
  grouping erp-data-channel {
    leaf-list vlan {
      type string;
      description "VLAN ID or VLAN ID range [1..4094]";
      ordered-by user;
    }
  }
  grouping erp-interface {
    container control-channel {
      description "Control channel of ring port";
      presence "enable control-channel";
      leaf vlan {
        type uint16 {
          range "1 .. 4094";
        }
        description "Dedicated VLAN identifier";
      }
      leaf control-channel-name {
        type "jt:interface-name";
      }
    }
    leaf ring-protection-link-end {
      type empty;
      description "Port is connecting to ring protection link";
    }
    leaf interface-none {
      type empty;
      description "Port is not used";
    }
  }
  grouping juniper-protocols-rip {
    container traceoptions {
      description "Trace options for RIP";
      container file {
        description "Trace file options";
        leaf filename {
          type string {
            length "1 .. 1024";
          }
          description "Name of file in which to write trace information";
        }
        leaf replace {
          type empty;
          description "Replace trace file rather than appending to it";
          status deprecated;
        }
        leaf size {
          type string;
          description "Maximum trace file size";
        }
        leaf files {
          type uint32 {
            range "2 .. 1000";
          }
          default "10";
          description "Maximum number of trace files";
        }
        leaf no-stamp {
          type empty;
          description "Do not timestamp trace file";
          status deprecated;
        }
        choice world-readable-choice {
          leaf world-readable {
            type empty;
            description "Allow any user to read the log file";
          }
          leaf no-world-readable {
            type empty;
            description "Don't allow any user to read the log file";
          }
        }
      }
      list flag {
        description "Tracing parameters";
        key name;
        ordered-by user;
        leaf name {
          type enumeration {
            enum auth {
              description "Trace RIP authentication";
            }
            enum error {
              description "Trace RIP errors";
            }
            enum expiration {
              description "Trace RIP route expiration processing";
            }
            enum holddown {
              description "Trace RIP hold-down processing";
            }
            enum packets {
              description "Trace all RIP packets";
            }
            enum request {
              description "Trace RIP information packets";
            }
            enum trigger {
              description "Trace RIP triggered updates";
            }
            enum update {
              description "Trace RIP update packets";
            }
            enum nsr-synchronization {
              description "Trace NSR synchronization events";
            }
            enum route {
              description "Trace routing information";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
        leaf send {
          type empty;
          description "Trace transmitted packets";
        }
        leaf receive {
          type empty;
          description "Trace received packets";
        }
        leaf detail {
          type empty;
          description "Trace detailed information";
        }
        leaf disable {
          type empty;
          description "Disable this trace flag";
        }
        container filter {
          description "Filter to apply to this flag";
          presence "enable filter";
          uses rip_filter_obj;
        }
      }
    }
    container rib-group {
      description "Routing table group for importing RIP routes";
      uses rib_group_inet_type;
    }
    leaf metric-in {
      type uint32 {
        range "1 .. 15";
      }
      description "Metric value to add to incoming routes";
    }
    container send {
      description "Configure RIP send options";
      choice send-opts {
        case case_1 {
          leaf broadcast {
            type empty;
            description "Broadcast RIPv2 packets (RIPv1 compatible)";
          }
        }
        case case_2 {
          leaf multicast {
            type empty;
            description "Multicast RIPv2 packets";
          }
        }
        case case_3 {
          leaf none {
            type empty;
            description "Do not send RIP updates";
          }
        }
        case case_4 {
          leaf version-1 {
            type empty;
            description "Broadcast RIPv1 packets";
          }
        }
      }
    }
    container receive {
      description "Configure RIP receive options";
      choice receive-opts {
        case case_1 {
          leaf both {
            type empty;
            description "Accept both RIPv1 and RIPv2 packets";
          }
        }
        case case_2 {
          leaf none {
            type empty;
            description "Do not receive RIP packets";
          }
        }
        case case_3 {
          leaf version-1 {
            type empty;
            description "Accept RIPv1 packets only";
          }
        }
        case case_4 {
          leaf version-2 {
            type empty;
            description "Accept only RIPv2 packets";
          }
        }
      }
    }
    choice check-zero-choice {
      leaf check-zero {
        type empty;
        description "Check reserved fields on incoming RIPv2 packets";
      }
      leaf no-check-zero {
        type empty;
        description "Don't check reserved fields on incoming RIPv2 packets";
      }
    }
    leaf message-size {
      type uint32 {
        range "25 .. 255";
      }
      description "Number of route entries per update message";
    }
    leaf-list import {
      type "jt:policy-algebra";
      description "Import policy";
      ordered-by user;
    }
    leaf holddown {
      type uint32 {
        range "10 .. 180";
      }
      description "Hold-down time";
      units seconds;
    }
    leaf route-timeout {
      type uint32 {
        range "30 .. 360";
      }
      description "Delay before routes time out";
      units seconds;
    }
    leaf update-interval {
      type uint32 {
        range "10 .. 60";
      }
      description "Interval between regular route updates";
      units seconds;
    }
    choice authentication {
      case case_1 {
        leaf authentication-type {
          type enumeration {
            enum none {
              description "No authentication";
            }
            enum simple {
              description "Simple password authentication";
            }
            enum md5 {
              description "MD5 authentication";
            }
          }
        }
      }
      case case_2 {
        list authentication-selective-md5 {
          description "MD5 authentication with one or more keys";
          key name;
          ordered-by user;
          leaf name {
            type uint32 {
              range "0 .. 255";
            }
            description "Key ID for MD5 authentication";
          }
          leaf key {
            type "jt:unreadable";
            description "MD5 authentication key value";
          }
          leaf start-time {
            type "jt:time";
            description "Start time for key transmission (YYYY-MM-DD.HH:MM)";
          }
        }
      }
    }
    leaf authentication-key {
      type "jt:unreadable";
      description "Authentication key (password)";
    }
    list group {
      description "Instance configuration";
      key name;
      ordered-by user;
      leaf name {
        type string;
        description "Group name";
      }
      leaf route-timeout {
        type uint32 {
          range "30 .. 360";
        }
        description "Delay before routes time out";
        units seconds;
      }
      leaf update-interval {
        type uint32 {
          range "10 .. 60";
        }
        description "Interval between regular route updates";
        units seconds;
      }
      leaf preference {
        type uint32;
        description "Preference of routes learned by this group";
      }
      leaf metric-out {
        type uint32 {
          range "1 .. 15";
        }
        description "Default metric of exported routes";
      }
      leaf-list export {
        type "jt:policy-algebra";
        description "Export policy";
        ordered-by user;
      }
      leaf-list import {
        type "jt:policy-algebra";
        description "Import policy";
        ordered-by user;
      }
      leaf demand-circuit {
        type empty;
        description "Enable demand circuit on this interface";
      }
      leaf max-retrans-time {
        type uint32 {
          range "5 .. 180";
        }
        description "Maximum time to re-transmit a message in demand-circuit";
      }
      container bfd-liveness-detection {
        description "Bidirectional Forwarding Detection options";
        leaf version {
          type enumeration {
            enum 0 {
              description "BFD version 0 (deprecated)";
            }
            enum 1 {
              description "BFD version 1";
            }
            enum automatic {
              description "Choose BFD version automatically";
            }
          }
          default "automatic";
          description "BFD protocol version number";
        }
        leaf minimum-interval {
          type uint32 {
            range "1 .. 255000";
          }
          description "Minimum transmit and receive interval";
          units milliseconds;
        }
        leaf minimum-transmit-interval {
          type uint32 {
            range "1 .. 255000";
          }
          description "Minimum transmit interval";
          status deprecated;
          units milliseconds;
        }
        leaf minimum-receive-interval {
          type uint32 {
            range "1 .. 255000";
          }
          description "Minimum receive interval";
          units milliseconds;
        }
        leaf multiplier {
          type uint32 {
            range "1 .. 255";
          }
          default "3";
          description "Detection time multiplier";
        }
        leaf inline-disable {
          type empty;
          description "Disable inline mode for this BFD session";
        }
        leaf pdu-size {
          type uint32 {
            range "24 .. 9000";
          }
          default "24";
          description "BFD transport protocol payload size";
        }
        choice adaptation-choice {
          case case_1 {
            leaf no-adaptation {
              type empty;
              description "Disable adaptation";
            }
          }
        }
        container transmit-interval {
          description "Transmit-interval options";
          leaf minimum-interval {
            type uint32 {
              range "1 .. 255000";
            }
            description "Minimum transmit interval";
            units milliseconds;
          }
          leaf threshold {
            type uint32;
            description "High transmit interval triggering a trap";
            units milliseconds;
          }
        }
        container detection-time {
          description "Detection-time options";
          leaf threshold {
            type uint32;
            description "High detection-time triggering a trap";
            units milliseconds;
          }
        }
        container authentication {
          description "Authentication options";
          leaf key-chain {
            type string;
            description "Key chain name";
          }
          leaf algorithm {
            type enumeration {
              enum simple-password {
                description "Simple password";
              }
              enum keyed-md5 {
                description "Keyed message Digest 5";
              }
              enum meticulous-keyed-md5 {
                description "Meticulous keyed message Digest 5";
              }
              enum keyed-sha-1 {
                description "Keyed secure hash algorithm (SHA1) ";
              }
              enum meticulous-keyed-sha-1 {
                description "Meticulous keyed secure hash algorithm (SHA1) ";
              }
            }
            description "Algorithm name";
          }
          leaf loose-check {
            type empty;
            description "Verify authentication only if authentication is negotiated";
          }
        }
      }
      list neighbor {
        description "Neighbor configuration";
        key name;
        ordered-by user;
        leaf name {
          type "jt:interface-name";
          description "Interface name";
        }
        leaf route-timeout {
          type uint32 {
            range "30 .. 360";
          }
          description "Delay before routes time out";
          units seconds;
        }
        leaf update-interval {
          type uint32 {
            range "10 .. 60";
          }
          description "Interval between regular route updates";
          units seconds;
        }
        leaf interface-type {
          type enumeration {
            enum p2mp {
              description "Point-to-multipoint link";
            }
          }
          description "Interface type for the neighbor";
        }
        leaf dynamic-peers {
          type empty;
          description "Learn peers dynamically on a p2mp interface";
        }
        list peer {
          description "P2MP peer";
          key name;
          ordered-by user;
          leaf name {
            type "jt:ipaddr";
            description "Address of peer";
          }
        }
        leaf metric-in {
          type uint32 {
            range "1 .. 15";
          }
          description "Metric value to add to incoming routes";
        }
        container send {
          description "Configure RIP send options";
          choice send-opts {
            case case_1 {
              leaf broadcast {
                type empty;
                description "Broadcast RIPv2 packets (RIPv1 compatible)";
              }
            }
            case case_2 {
              leaf multicast {
                type empty;
                description "Multicast RIPv2 packets";
              }
            }
            case case_3 {
              leaf none {
                type empty;
                description "Do not send RIP updates";
              }
            }
            case case_4 {
              leaf version-1 {
                type empty;
                description "Broadcast RIPv1 packets";
              }
            }
          }
        }
        container receive {
          description "Configure RIP receive options";
          choice receive-opts {
            case case_1 {
              leaf both {
                type empty;
                description "Accept both RIPv1 and RIPv2 packets";
              }
            }
            case case_2 {
              leaf none {
                type empty;
                description "Do not receive RIP packets";
              }
            }
            case case_3 {
              leaf version-1 {
                type empty;
                description "Accept RIPv1 packets only";
              }
            }
            case case_4 {
              leaf version-2 {
                type empty;
                description "Accept only RIPv2 packets";
              }
            }
          }
        }
        leaf demand-circuit {
          type empty;
          description "Enable demand circuit on this interface";
        }
        leaf max-retrans-time {
          type uint32 {
            range "5 .. 180";
          }
          description "Maximum time to re-transmit a msg in demand-circuit";
        }
        choice check-zero-choice {
          leaf check-zero {
            type empty;
            description "Check reserved fields on incoming RIPv1 packets";
          }
          leaf no-check-zero {
            type empty;
            description "Don't check reserved fields on incoming RIPv1 packets";
          }
        }
        leaf any-sender {
          type empty;
          description "Disable strict checks on sender address";
        }
        leaf message-size {
          type uint32 {
            range "25 .. 255";
          }
          description "Number of route entries per update message";
        }
        leaf-list import {
          type "jt:policy-algebra";
          description "Import policy";
          ordered-by user;
        }
        choice authentication {
          case case_1 {
            leaf authentication-type {
              type enumeration {
                enum none {
                  description "No authentication";
                }
                enum simple {
                  description "Simple password authentication";
                }
                enum md5 {
                  description "MD5 authentication";
                }
              }
            }
          }
          case case_2 {
            list authentication-selective-md5 {
              description "MD5 authentication with one or more keys";
              key name;
              ordered-by user;
              leaf name {
                type uint32 {
                  range "0 .. 255";
                }
                description "Key ID for MD5 authentication";
              }
              leaf key {
                type "jt:unreadable";
                description "MD5 authentication key value";
              }
              leaf start-time {
                type "jt:time";
                description "Start time for key transmission (YYYY-MM-DD.HH:MM)";
              }
            }
          }
        }
        leaf authentication-key {
          type "jt:unreadable";
          description "Authentication key (password)";
        }
        container bfd-liveness-detection {
          description "Bidirectional Forwarding Detection options";
          leaf version {
            type enumeration {
              enum 0 {
                description "BFD version 0 (deprecated)";
              }
              enum 1 {
                description "BFD version 1";
              }
              enum automatic {
                description "Choose BFD version automatically";
              }
            }
            default "automatic";
            description "BFD protocol version number";
          }
          leaf minimum-interval {
            type uint32 {
              range "1 .. 255000";
            }
            description "Minimum transmit and receive interval";
            units milliseconds;
          }
          leaf minimum-transmit-interval {
            type uint32 {
              range "1 .. 255000";
            }
            description "Minimum transmit interval";
            status deprecated;
            units milliseconds;
          }
          leaf minimum-receive-interval {
            type uint32 {
              range "1 .. 255000";
            }
            description "Minimum receive interval";
            units milliseconds;
          }
          leaf multiplier {
            type uint32 {
              range "1 .. 255";
            }
            default "3";
            description "Detection time multiplier";
          }
          leaf inline-disable {
            type empty;
            description "Disable inline mode for this BFD session";
          }
          leaf pdu-size {
            type uint32 {
              range "24 .. 9000";
            }
            default "24";
            description "BFD transport protocol payload size";
          }
          choice adaptation-choice {
            case case_1 {
              leaf no-adaptation {
                type empty;
                description "Disable adaptation";
              }
            }
          }
          container transmit-interval {
            description "Transmit-interval options";
            leaf minimum-interval {
              type uint32 {
                range "1 .. 255000";
              }
              description "Minimum transmit interval";
              units milliseconds;
            }
            leaf threshold {
              type uint32;
              description "High transmit interval triggering a trap";
              units milliseconds;
            }
          }
          container detection-time {
            description "Detection-time options";
            leaf threshold {
              type uint32;
              description "High detection-time triggering a trap";
              units milliseconds;
            }
          }
          container authentication {
            description "Authentication options";
            leaf key-chain {
              type string;
              description "Key chain name";
            }
            leaf algorithm {
              type enumeration {
                enum simple-password {
                  description "Simple password";
                }
                enum keyed-md5 {
                  description "Keyed message Digest 5";
                }
                enum meticulous-keyed-md5 {
                  description "Meticulous keyed message Digest 5";
                }
                enum keyed-sha-1 {
                  description "Keyed secure hash algorithm (SHA1) ";
                }
                enum meticulous-keyed-sha-1 {
                  description "Meticulous keyed secure hash algorithm (SHA1) ";
                }
              }
              description "Algorithm name";
            }
            leaf loose-check {
              type empty;
              description "Verify authentication only if authentication is negotiated";
            }
          }
        }
      }
    }
    container graceful-restart {
      description "RIP graceful restart options";
      presence "enable graceful-restart";
      choice enable-disable {
        case case_1 {
          leaf disable {
            type empty;
            description "Disable graceful restart";
          }
        }
      }
      leaf restart-time {
        type uint32 {
          range "1 .. 600";
        }
        description "Time after which RIP is declared out of restart";
      }
    }
  }
  grouping juniper-protocols-ripng {
    container traceoptions {
      description "Trace options for RIPng";
      container file {
        description "Trace file options";
        leaf filename {
          type string {
            length "1 .. 1024";
          }
          description "Name of file in which to write trace information";
        }
        leaf replace {
          type empty;
          description "Replace trace file rather than appending to it";
          status deprecated;
        }
        leaf size {
          type string;
          description "Maximum trace file size";
        }
        leaf files {
          type uint32 {
            range "2 .. 1000";
          }
          default "10";
          description "Maximum number of trace files";
        }
        leaf no-stamp {
          type empty;
          description "Do not timestamp trace file";
          status deprecated;
        }
        choice world-readable-choice {
          leaf world-readable {
            type empty;
            description "Allow any user to read the log file";
          }
          leaf no-world-readable {
            type empty;
            description "Don't allow any user to read the log file";
          }
        }
      }
      list flag {
        description "Tracing parameters";
        key name;
        ordered-by user;
        leaf name {
          type enumeration {
            enum error {
              description "Trace RIPng errors";
            }
            enum expiration {
              description "Trace RIPng route expiration processing";
            }
            enum holddown {
              description "Trace RIPng hold-down processing";
            }
            enum packets {
              description "Trace all RIPng packets";
            }
            enum request {
              description "Trace RIPng information packets";
            }
            enum trigger {
              description "Trace RIPng triggered updates";
            }
            enum update {
              description "Trace RIPng update packets";
            }
            enum nsr-synchronization {
              description "Trace NSR synchronization events";
            }
            enum route {
              description "Trace routing information";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
        leaf send {
          type empty;
          description "Trace transmitted packets";
        }
        leaf receive {
          type empty;
          description "Trace received packets";
        }
        leaf detail {
          type empty;
          description "Trace detailed information";
        }
        leaf disable {
          type empty;
          description "Disable this trace flag";
        }
      }
    }
    leaf metric-in {
      type uint32 {
        range "1 .. 15";
      }
      description "Metric value to add to incoming routes";
    }
    container send {
      description "Configure RIPng send options";
      choice send-opts {
        case case_1 {
          leaf none {
            type empty;
            description "Do not send RIPng updates";
          }
        }
      }
    }
    container receive {
      description "Configure RIPng receive options";
      choice receive-opts {
        case case_1 {
          leaf none {
            type empty;
            description "Do not receive RIPng packets";
          }
        }
      }
    }
    leaf-list import {
      type "jt:policy-algebra";
      description "Import policy";
      ordered-by user;
    }
    leaf holddown {
      type uint32 {
        range "10 .. 180";
      }
      description "Hold-down time";
      units seconds;
    }
    leaf route-timeout {
      type uint32 {
        range "30 .. 360";
      }
      description "Delay before routes time out";
      units seconds;
    }
    leaf update-interval {
      type uint32 {
        range "10 .. 60";
      }
      description "Interval between regular route updates";
      units seconds;
    }
    list group {
      description "Instance configuration";
      key name;
      ordered-by user;
      leaf name {
        type string;
        description "Group name";
      }
      leaf route-timeout {
        type uint32 {
          range "30 .. 360";
        }
        description "Delay before routes time out";
        units seconds;
      }
      leaf update-interval {
        type uint32 {
          range "10 .. 60";
        }
        description "Interval between regular route updates";
        units seconds;
      }
      leaf preference {
        type uint32;
        description "Preference of routes learned by this group";
      }
      leaf metric-out {
        type uint32 {
          range "1 .. 15";
        }
        description "Default metric of exported routes";
      }
      leaf-list export {
        type "jt:policy-algebra";
        description "Export policy";
        ordered-by user;
      }
      leaf-list import {
        type "jt:policy-algebra";
        description "Import policy";
        ordered-by user;
      }
      list neighbor {
        description "Neighbor configuration";
        key name;
        ordered-by user;
        leaf name {
          type "jt:interface-name";
          description "Interface name";
        }
        leaf route-timeout {
          type uint32 {
            range "30 .. 360";
          }
          description "Delay before routes time out";
          units seconds;
        }
        leaf update-interval {
          type uint32 {
            range "10 .. 60";
          }
          description "Interval between regular route updates";
          units seconds;
        }
        leaf metric-in {
          type uint32 {
            range "1 .. 15";
          }
          description "Metric value to add to incoming routes";
        }
        container send {
          description "Configure RIPng send options";
          choice send-opts {
            case case_1 {
              leaf none {
                type empty;
                description "Do not send RIPng updates";
              }
            }
          }
        }
        container receive {
          description "Configure RIPng receive options";
          choice receive-opts {
            case case_1 {
              leaf none {
                type empty;
                description "Do not receive RIPng packets";
              }
            }
          }
        }
        leaf-list import {
          type "jt:policy-algebra";
          description "Import policy";
          ordered-by user;
        }
      }
    }
    container graceful-restart {
      description "RIPng graceful restart options";
      presence "enable graceful-restart";
      choice enable-disable {
        case case_1 {
          leaf disable {
            type empty;
            description "Disable graceful restart";
          }
        }
      }
      leaf restart-time {
        type uint32 {
          range "1 .. 600";
        }
        description "Time after which RIPng is declared out of restart";
      }
    }
  }
  grouping juniper-protocols-router-discovery {
    choice enable-disable {
      case case_1 {
        leaf disable {
          type empty;
          description "Disable router discovery";
        }
      }
    }
    container traceoptions {
      description "Trace options for router discovery";
      container file {
        description "Trace file options";
        leaf filename {
          type string {
            length "1 .. 1024";
          }
          description "Name of file in which to write trace information";
        }
        leaf replace {
          type empty;
          description "Replace trace file rather than appending to it";
          status deprecated;
        }
        leaf size {
          type string;
          description "Maximum trace file size";
        }
        leaf files {
          type uint32 {
            range "2 .. 1000";
          }
          default "10";
          description "Maximum number of trace files";
        }
        leaf no-stamp {
          type empty;
          description "Do not timestamp trace file";
          status deprecated;
        }
        choice world-readable-choice {
          leaf world-readable {
            type empty;
            description "Allow any user to read the log file";
          }
          leaf no-world-readable {
            type empty;
            description "Don't allow any user to read the log file";
          }
        }
      }
      list flag {
        description "Tracing parameters";
        key name;
        ordered-by user;
        leaf name {
          type enumeration {
            enum route {
              description "Trace routing information";
            }
            enum normal {
              description "Trace normal events";
            }
            enum general {
              description "Trace general events";
            }
            enum state {
              description "Trace state transitions";
            }
            enum policy {
              description "Trace policy processing";
            }
            enum task {
              description "Trace routing protocol task processing";
            }
            enum timer {
              description "Trace routing protocol timer processing";
            }
            enum all {
              description "Trace everything";
            }
          }
        }
      }
    }
    list interface {
      description "Interfaces on which to configure router discovery";
      key name;
      ordered-by user;
      leaf name {
        type "jt:interface-name";
        description "Interface name";
      }
      leaf max-advertisement-interval {
        type uint32 {
          range "4 .. 1800";
        }
        description "Maximum time before sending advertisements";
        units seconds;
      }
      leaf min-advertisement-interval {
        type uint32 {
          range "3 .. 1800";
        }
        description "Minimum time before sending advertisements";
        units seconds;
      }
      leaf lifetime {
        type uint32 {
          range "3 .. 9000";
        }
        description "How long addresses in advertisements are valid";
        units seconds;
      }
    }
    list address {
      description "IP addresses to include in advertisements";
      key name;
      ordered-by user;
      leaf name {
        type "jt:ipv4addr";
        description "IP addresses to include in router advertisements";
      }
      leaf advertise {
        type empty;
        description "Advertise the IP address in advertisements";
      }
      leaf ignore {
        type empty;
        description "Do not advertise the IP address in advertisements";
      }
      leaf broadcast {
        type empty;
        description "Include IP address only in broadcast advertisements";
      }
      leaf multicast {
        type empty;
        description "Include IP address only in multicast advertisements";
      }
      leaf ineligible {
        type empty;
        description "IP address can never become a default router";
      }
      leaf priority {
        type int32;
        description "Preference of the address to become a default router";
      }
    }
  }
  grouping juniper-protocols-rsvp {
    description "RSVP options";
    choice enable-disable {
      case case_1 {
        leaf disable {
          type empty;
          description "Disable RSVP";
        }
      }
    }
    container graceful-restart {
      description "Configure graceful restart attributes";
      choice enable-disable {
        case case_1 {
          leaf disable {
            type empty;
            description "Disable RSVP graceful restart capability";
          }
        }
      }
      leaf helper-disable {
        type empty;
        description "Disable graceful restart helper capability";
      }
      leaf maximum-helper-restart-time {
        type uint32 {
          range "1 .. 1800";
        }
        default "20";
        description "Maximum wait time from down event to neighbor dead";
        units seconds;
      }
      leaf maximum-helper-recovery-time {
        type uint32 {
          range "1 .. 3600";
        }
        default "180";
        description "Maximum time restarting neighbor states are kept";
        units seconds;
      }
    }
    container tunnel-services {
      description "Use tunnel services for P2MP LSP ultimate-hop popping";
      presence "enable tunnel-services";
      leaf-list devices {
        type "jt:interface-device";
        description "Tunnel services devices to use for P2MP LSPs";
        ordered-by user;
      }
    }
    leaf no-p2mp-sublsp {
      type empty;
      description "Disable P2MP sub-LSP object generation";
    }
    leaf no-node-id-subobject {
      type empty;
      description "Do not include the node-id sub-object in the RRO";
    }
    leaf no-interface-hello {
      type empty;
      description "Disble interface Hellos on all RSVP interfaces";
    }
    container pop-and-forward {
      description "RSVP pop-and-forward specific global parameters";
      container application-label {
        description "Number of application labels under the RSVP transport";
        leaf depth {
          type uint32 {
            range "0 .. 3";
          }
          default "1";
          description "Application label depth";
        }
      }
    }
    leaf hello-acknowledgements {
      type empty;
      description "Acknowledge Hellos on RSVP interfaces not having sessions";
    }
    leaf no-hello-acknowledgements {
      type empty;
      description "Do not ack Hellos on RSVP interfaces not having sessions";
    }
    container node-hello {
      description "Enable node-ID based Hellos on all RSVP interfaces";
      presence "enable node-hello";
      leaf hello-interval {
        type uint32 {
          range "0 .. 60";
        }
        default "9";
        description "Hello interval";
        units seconds;
      }
    }
    leaf no-node-hello {
      type empty;
      description "Disable node-ID based Hellos on the router";
    }
    leaf allow-bidirectional {
      type empty;
      description "Enable bidirectional support in RSVP";
      status deprecated;
    }
    leaf local-reversion {
      type empty;
      description "Enable local reversion at this Point of Local Repair";
    }
    leaf no-local-reversion {
      type empty;
      description "Disable local reversion at this Point of Local Repair";
    }
    leaf rfc6510-lsp-attributes {
      type empty;
      description "Use RFC6510 compliant LSP_ATTRIBUTES";
    }
    container fast-reroute {
      description "One-to-one fast-reroute protection mechanism";
      leaf optimize-timer {
        type int32 {
          range "0 .. 65535";
        }
        description "Frequency of reoptimization for fast-reroute detour";
        units seconds;
      }
    }
    container load-balance {
      description "Per-packet load-balancing algorithm";
      leaf bandwidth {
        type empty;
        description "Per-packet load balancing proportional to LSP bandwidth";
      }
    }
    container traceoptions {
      description "Trace options for RSVP";
      container file {
        description "Trace file options";
        leaf filename {
          type string {
            length "1 .. 1024";
          }
          description "Name of file in which to write trace information";
        }
        leaf replace {
          type empty;
          description "Replace trace file rather than appending to it";
          status deprecated;
        }
        leaf size {
          type string;
          description "Maximum trace file size";
        }
        leaf files {
          type uint32 {
            range "2 .. 1000";
          }
          default "10";
          description "Maximum number of trace files";
        }
        leaf no-stamp {
          type empty;
          description "Do not timestamp trace file";
          status deprecated;
        }
        choice world-readable-choice {
          leaf world-readable {
            type empty;
            description "Allow any user to read the log file";
          }
          leaf no-world-readable {
            type empty;
            description "Don't allow any user to read the log file";
          }
        }
      }
      list flag {
        description "Tracing parameters";
        key name;
        ordered-by user;
        leaf name {
          type enumeration {
            enum io-event {
              description "Trace RSVP IO task related events";
            }
            enum io-packets {
              description "Trace all RSVP periodic refresh activity";
            }
            enum packets {
              description "Trace all RSVP trigger packets";
            }
            enum path {
              description "Trace RSVP trigger path messages";
            }
            enum resv {
              description "Trace RSVP trigger Resv messages";
            }
            enum pathtear {
              description "Trace RSVP PathTear messages";
            }
            enum resvtear {
              description "Trace RSVP ResvTear messages";
            }
            enum state {
              description "Trace state transitions";
            }
            enum error {
              description "Trace error conditions";
            }
            enum route {
              description "Trace routing information";
            }
            enum lmp {
              description "Trace RSVP-LMP related interactions";
            }
            enum event {
              description "Trace RSVP related events";
            }
            enum nsr-synchronization {
              description "Trace NSR synchronization events";
            }
            enum lsp-prefix {
              description "Prefix the trace messages with LSP information";
            }
            enum enhanced-frr {
              description "Enhanced FRR related information";
            }
            enum all {
              description "Trace everything";
            }
          }
        }
        leaf send {
          type empty;
          description "Trace transmitted packets";
        }
        leaf receive {
          type empty;
          description "Trace received packets";
        }
        leaf detail {
          type empty;
          description "Trace detailed information";
        }
        leaf disable {
          type empty;
          description "Disable this trace flag";
        }
      }
    }
    leaf refresh-time {
      type uint32 {
        range "1 .. 65535";
      }
      default "1200";
      description "Refresh time in seconds";
    }
    leaf keep-multiplier {
      type uint32 {
        range "1 .. 255";
      }
      default "3";
      description "Keep multiplier";
    }
    leaf graceful-deletion-timeout {
      type uint32 {
        range "1 .. 300";
      }
      default "30";
      description "Time to complete graceful deletion signaling";
      units seconds;
    }
    leaf setup-protection {
      type empty;
      description "Enable setup protection";
    }
    leaf no-p2mp-re-merge {
      type empty;
      description "Enable p2mp remerge";
    }
    leaf cross-credibility-cspf {
      type empty;
      description "Compute CSPF paths spanning protocols for bypass LSP, detour LSP and loose hop expansion";
    }
    container preemption {
      description "Set RSVP session preemption attributes";
      choice preemption-type {
        case case_1 {
          leaf disabled {
            type empty;
            description "No RSVP session preemption";
          }
        }
        case case_2 {
          leaf normal {
            type empty;
            description "Run RSVP session preemption to accommodate new sessions";
          }
        }
        case case_3 {
          leaf aggressive {
            type empty;
            description "Run RSVP session preemption whenever necessary";
          }
        }
      }
      container soft-preemption {
        description "Options for establishing new path before tearing down a preempted LSP";
        leaf cleanup-timer {
          type int32 {
            range "0 .. 10800";
          }
          description "Time a soft-preempted LSP will be maintained";
          units seconds;
        }
      }
    }
    leaf authentication-key {
      type "jt:unreadable";
      description "Authentication password";
    }
    leaf no-authentication-check {
      type empty;
      description "Skip authentication check for received messages";
    }
    container associated-bidirectional-lsp {
      description "Set associated bidirectional LSP attributes";
      leaf single-sided-provisioning {
        type empty;
        description "Enable unidirectional reverse LSP setup for single sided provisioned forward LSP";
      }
    }
    leaf no-enhanced-frr-bypass {
      type empty;
      description "Disable enhanced facility backup FRR";
    }
    leaf no-node-hello-on-bypass {
      type empty;
      description "Do not send NodeID hello over bypass LSP";
    }
    container expand-flood-reflector-hop {
      description "Control expansion of flood reflector ERO strict hops";
      presence "enable expand-flood-reflector-hop";
    }
    list interface {
      description "RSVP interface options";
      key name;
      ordered-by user;
      leaf name {
        type "jt:interface-name";
        description "Interface name";
      }
      choice enable-disable {
        case case_1 {
          leaf disable {
            type empty;
            description "Disable RSVP on this interface";
          }
        }
      }
      leaf authentication-key {
        type "jt:unreadable";
        description "Authentication password";
      }
      choice aggregate-choice {
        leaf aggregate {
          type empty;
          description "Permit refresh reduction extensions on the interface";
          status deprecated;
        }
        leaf no-aggregate {
          type empty;
          description "Don't permit refresh reduction extensions on the interface";
          status deprecated;
        }
      }
      choice reliable-choice {
        leaf reliable {
          type empty;
          description "Permit reliable message delivery on the interface";
        }
        leaf no-reliable {
          type empty;
          description "Don't permit reliable message delivery on the interface";
        }
      }
      leaf hello-interval {
        type uint32 {
          range "0 .. 60";
        }
        default "9";
        description "Hello interval";
        units seconds;
      }
      container subscription {
        description "Link bandwidth percentage for RSVP reservation";
        uses subscription-type;
      }
      leaf bandwidth {
        type string;
        description "Available bandwidth for the interface units bps";
      }
      container update-threshold {
        description "Change in reserved bandwidth to trigger IGP update";
        container adaptive {
          description "Tune update-threshold dynamically";
          list limit {
            description "Available Bandwidth threshold limit";
            key name;
            leaf name {
              type string;
              description "Upper limit of Available bandwidth for this range";
            }
            leaf threshold-percent {
              type decimal64 {
                fraction-digits 9;
                range "0.001 .. 20";
              }
              default "10.0";
              description "Percentage change in reserved bandwidth to trigger IGP update";
              units percent;
            }
            leaf threshold-value {
              type string;
              description "Change in reserved bandwidth to trigger IGP update (will be capped at 20% of link BW)";
            }
          }
        }
        leaf threshold-percent {
          type decimal64 {
            fraction-digits 9;
            range "0.001 .. 20";
          }
          default "10.0";
          description "Percentage change in reserved bandwidth to trigger IGP update";
          units percent;
        }
        leaf threshold-value {
          type string;
          description "Change in reserved bandwidth to trigger IGP update (will be capped at 20% of link BW)";
        }
      }
      container update-threshold-max-reservable {
        description "Change in non-rsvp bandwidth to trigger IGP update ";
        leaf bandwidth {
          type string;
          description "Change in non-rsvp bandwidth to trigger IGP update units bps";
        }
        leaf percent {
          type uint32 {
            range "1 .. 100";
          }
          description "Percentage change in max-reservable bandwidth to trigger IGP update";
          units percent;
        }
      }
      container non-rsvp-bandwdith {
        description "Config knobs relating to non-rsvp bandwidth";
        leaf local-bw-override-threshold {
          type empty;
          description "Overide threshold and update local bandwidth with non-rsvp bandwidth usage";
        }
      }
      container link-protection {
        description "Protect traffic with a label-stacked LSP";
        presence "enable link-protection";
        choice enable-disable {
          case case_1 {
            leaf disable {
              type empty;
              description "Disable link protection on this interface";
            }
          }
        }
        container bandwidth {
          description "Bandwidth for each bypass";
          uses bandwidth-type;
        }
        leaf max-bypasses {
          type uint32 {
            range "0 .. 99";
          }
          default "1";
          description "Max number of bypasses permitted for protecting this interface";
        }
        leaf subscription {
          type uint32 {
            range "1 .. 65535";
          }
          default "100";
          description "Percent of bandwidth guaranteed when admitting protected LSPs into bypasses";
        }
        leaf no-node-protection {
          type empty;
          description "Disallow node protection on this interface";
        }
        leaf optimize-timer {
          type uint32 {
            range "0 .. 65535";
          }
          default "0";
          description "Interval between bypass reoptimizations";
          units seconds;
        }
        leaf class-of-service {
          type int32 {
            range "0 .. 7";
          }
          description "Class of service for the bypass LSP";
        }
        leaf hop-limit {
          type uint32 {
            range "2 .. 255";
          }
          description "Maximum allowed router hops for bypass";
        }
        leaf no-cspf {
          type empty;
          description "Disable automatic path computation";
        }
        leaf exclude-srlg {
          type empty;
          description "Exclude SRLG links";
        }
        container priority {
          description "Preemption priorities for the bypass LSP";
          presence "enable priority";
        }
        leaf setup-priority {
          type uint32 {
            range "0 .. 7";
          }
          description "Set-up priority";
        }
        leaf reservation-priority {
          type uint32 {
            range "0 .. 7";
          }
          description "Reservation priority";
        }
        list path {
          description "Explicit route of bypass path";
          key name;
          ordered-by user;
          leaf name {
            type "jt:ipv4addr";
            description "Address of next system in path";
          }
          choice loose_strict_none {
            case case_1 {
              leaf loose {
                type empty;
                description "Next hop might not be adjacent";
              }
            }
            case case_2 {
              leaf strict {
                type empty;
                description "Next hop must be adjacent";
              }
            }
          }
        }
        container admin-group {
          description "Administrative group policy";
          uses admin_group_include_exclude;
        }
        list bypass {
          description "Bypass with specific constraints";
          key name;
          ordered-by user;
          leaf name {
            type string {
              length "1 .. 64";
            }
            description "Name of bypass";
          }
          leaf to {
            type "jt:ipv4addr";
            description "Address of egress router";
          }
          container bandwidth {
            description "Bandwidth for each bypass";
            uses bandwidth-type;
          }
          container subscription {
            description "Bandwidth percent available on bypass for protected LSPs";
            presence "enable subscription";
            uses bypass-subscription-type;
          }
          leaf description {
            type string {
              length "1 .. 80";
            }
            description "Text description of bypass";
          }
          container priority {
            description "Preemption priorities for bypass";
            presence "enable priority";
          }
          leaf setup-priority {
            type uint32 {
              range "0 .. 7";
            }
            description "Set-up priority";
          }
          leaf reservation-priority {
            type uint32 {
              range "0 .. 7";
            }
            description "Reservation priority";
          }
          leaf class-of-service {
            type int32 {
              range "0 .. 7";
            }
            description "Class of service for the bypass LSP";
          }
          leaf hop-limit {
            type uint32 {
              range "2 .. 255";
            }
            description "Maximum allowed router hops for bypass";
          }
          leaf no-cspf {
            type empty;
            description "Disable automatic path computation";
          }
          leaf exclude-srlg {
            type empty;
            description "Exclude SRLG links";
          }
          list path {
            description "Explicit route of bypass path";
            key name;
            ordered-by user;
            leaf name {
              type "jt:ipv4addr";
              description "Address of next system in path";
            }
            choice loose_strict_none {
              case case_1 {
                leaf loose {
                  type empty;
                  description "Next hop might not be adjacent";
                }
              }
              case case_2 {
                leaf strict {
                  type empty;
                  description "Next hop must be adjacent";
                }
              }
            }
          }
          container admin-group {
            description "Administrative group policy";
            uses admin_group_include_exclude;
          }
        }
        container optimize {
          description "Configure compute optimization algorithm";
          choice compute-algo {
            case case_1 {
              leaf bandwidth {
                type empty;
                description "Compute path optimized for available bandwidth";
              }
            }
          }
        }
      }
    }
    list peer-interface {
      description "Configuration for peer interface";
      key name;
      ordered-by user;
      leaf name {
        type string;
        description "Name of peer interface";
      }
      choice enable-disable {
        case case_1 {
          leaf disable {
            type empty;
            description "Disable RSVP on this control peer";
          }
        }
      }
      leaf authentication-key {
        type "jt:unreadable";
        description "Authentication password";
      }
      choice aggregate-choice {
        leaf aggregate {
          type empty;
          description "Permit refresh reduction extensions on the interface";
          status deprecated;
        }
        leaf no-aggregate {
          type empty;
          description "Don't permit refresh reduction extensions on the interface";
          status deprecated;
        }
      }
      choice reliable-choice {
        leaf reliable {
          type empty;
          description "Permit reliable message delivery on the interface";
        }
        leaf no-reliable {
          type empty;
          description "Don't permit reliable message delivery on the interface";
        }
      }
      leaf hello-interval {
        type uint32 {
          range "0 .. 60";
        }
        default "9";
        description "Hello interval";
        units seconds;
      }
      container dynamic-bidirectional-transport {
        description "Enable dynamic setup of bidirectional packet LSP for transporting non-packet GMPLS LSP";
        presence "enable dynamic-bidirectional-transport";
        leaf template {
          type string;
          description "Template for the dynamic bidirectional packet LSP";
        }
      }
    }
    list lsp-set {
      description "Configuration for lsp set";
      key name;
      ordered-by user;
      leaf name {
        type string;
        description "Name of lsp set";
      }
      choice enable-disable {
        case case_1 {
          leaf disable {
            type empty;
            description "Disable this lsp set";
          }
        }
      }
      container match-criteria {
        description "Match criteria for this lsp set";
        uses lsp-set-match-type;
      }
      container traceoptions {
        description "Trace options for this lsp set";
        container file {
          description "Trace file options";
          leaf filename {
            type string {
              length "1 .. 1024";
            }
            description "Name of file in which to write trace information";
          }
          leaf replace {
            type empty;
            description "Replace trace file rather than appending to it";
            status deprecated;
          }
          leaf size {
            type string;
            description "Maximum trace file size";
          }
          leaf files {
            type uint32 {
              range "2 .. 1000";
            }
            default "10";
            description "Maximum number of trace files";
          }
          leaf no-stamp {
            type empty;
            description "Do not timestamp trace file";
            status deprecated;
          }
          choice world-readable-choice {
            leaf world-readable {
              type empty;
              description "Allow any user to read the log file";
            }
            leaf no-world-readable {
              type empty;
              description "Don't allow any user to read the log file";
            }
          }
        }
        list flag {
          description "Tracing parameters";
          key name;
          ordered-by user;
          leaf name {
            type enumeration {
              enum io-event {
                description "Trace RSVP IO task related events";
              }
              enum io-packets {
                description "Trace all RSVP periodic refresh activity";
              }
              enum packets {
                description "Trace all RSVP packets";
              }
              enum path {
                description "Trace RSVP path messages";
              }
              enum resv {
                description "Trace RSVP Resv messages";
              }
              enum pathtear {
                description "Trace RSVP PathTear messages";
              }
              enum resvtear {
                description "Trace RSVP ResvTear messages";
              }
              enum state {
                description "Trace state transitions";
              }
              enum error {
                description "Trace error conditions";
              }
              enum route {
                description "Trace routing information";
              }
              enum lmp {
                description "Trace RSVP-LMP related interactions";
              }
              enum event {
                description "Trace RSVP related events";
              }
              enum nsr-synchronization {
                description "Trace NSR synchronization events";
              }
              enum lsp-prefix {
                description "Prefix the trace messages with LSP information";
              }
              enum enhanced-frr {
                description "Enhanced FRR related information";
              }
              enum all {
                description "Trace everything";
              }
            }
          }
          leaf send {
            type empty;
            description "Trace transmitted packets";
          }
          leaf receive {
            type empty;
            description "Trace received packets";
          }
          leaf detail {
            type empty;
            description "Trace detailed information";
          }
          leaf disable {
            type empty;
            description "Disable this trace flag";
          }
        }
      }
    }
  }
  grouping bypass-subscription-type {
    leaf subscription {
      type string;
      default "100";
      description "Subscription percentage for bandwidth protection";
    }
  }
  grouping juniper-protocols-stp {
    choice enable-disable {
      case case_1 {
        leaf disable {
          type empty;
          description "Disable STP";
        }
      }
    }
    leaf bpdu-destination-mac-address {
      type enumeration {
        enum provider-bridge-group {
          description "802.1ad provider bridge group address";
        }
      }
      description "Destination MAC address in the spanning tree BPDUs";
    }
    leaf bridge-priority {
      type string;
      description "Priority of the bridge (in increments of 4k - 0,4k,8k,..60k)";
    }
    leaf backup-bridge-priority {
      type string;
      description "Priority of the bridge (in increments of 4k - 4k,8k,..60k)";
    }
    leaf max-age {
      type uint16 {
        range "6 .. 40";
      }
      description "Maximum age of received protocol bpdu";
      units seconds;
    }
    leaf hello-time {
      type uint16 {
        range "1 .. 10";
      }
      description "Time interval between configuration BPDUs";
      units seconds;
    }
    leaf forward-delay {
      type uint16 {
        range "4 .. 30";
      }
      description "Time spent in listening or learning state";
      units seconds;
    }
    leaf system-identifier {
      type "jt:mac-unicast";
      description "Sytem identifier to represent this node";
    }
    container traceoptions {
      description "Tracing options for debugging protocol operation";
      uses stp-trace-options;
    }
    leaf vpls-flush-on-topology-change {
      type empty;
      description "Enable VPLS MAC flush on root protected CE interface receving topology change";
    }
    leaf priority-hold-time {
      type uint16 {
        range "1 .. 255";
      }
      description "Hold time before switching to primary priority when core domain becomes up";
      units seconds;
    }
    list system-id {
      description "System ID to IP mapping";
      key name;
      ordered-by user;
      uses system-id-ip-map;
    }
    list interface {
      description "Interface options";
      key name;
      uses stp-interface;
    }
    leaf extended-system-id {
      type uint16 {
        range "0 .. 4095";
      }
      description "Extended system identifier";
    }
    leaf force-version {
      type enumeration {
        enum stp {
          description "Spanning tree protocol";
        }
      }
      description "Force protocol version";
    }
    leaf bpdu-block-on-edge {
      type empty;
      description "Block BPDU on all interfaces configured as edge (BPDU Protect)";
    }
  }
  grouping juniper-protocols-vgd {
    container traceoptions {
      description "OVSDB trace options";
      leaf no-remote-trace {
        type empty;
        description "Disable remote tracing";
      }
      container file {
        description "Trace file information";
        leaf filename {
          type string {
            length "1 .. 1024";
          }
          description "Name of file in which to write trace information";
        }
        leaf size {
          type string;
          description "Maximum trace file size";
        }
        leaf files {
          type uint32 {
            range "2 .. 1000";
          }
          default "3";
          description "Maximum number of trace files";
        }
        choice world-readable-choice {
          leaf world-readable {
            type empty;
            description "Allow any user to read the log file";
          }
          leaf no-world-readable {
            type empty;
            description "Don't allow any user to read the log file";
          }
        }
        leaf match {
          type "jt:regular-expression";
          description "Regular expression for lines to be logged";
        }
        leaf microsecond-stamp {
          type empty;
          description "Timestamp with microsecond granularity";
        }
      }
      list flag {
        description "Tracing flag parameters";
        key name;
        ordered-by user;
        leaf name {
          type enumeration {
            enum interface {
              description "Trace OVSDB daemon interface events";
            }
            enum configuration {
              description "Trace OVSDB daemon configuration events";
            }
            enum core {
              description "Trace OVSDB daemon core events";
            }
            enum l2-client {
              description "Trace OVSDB daemon l2-client events";
            }
            enum ovs-client {
              description "Trace OVSDB daemon ovs-client events";
            }
            enum function {
              description "Trace OVSDB daemon function events";
            }
            enum netconf-client {
              description "Trace OVSDB daemon netconf-client events";
            }
            enum all {
              description "Trace everything";
            }
          }
        }
      }
    }
    list interfaces {
      description "Interfaces configured to be controlled by OVSDB";
      key name;
      ordered-by user;
      leaf name {
        type "jt:interface-unit";
        description "Interface name";
      }
    }
    list controller {
      description "Controller's IP address and port";
      key name;
      ordered-by user;
      leaf name {
        type "jt:ipaddr";
        description "Controller's IPv4 address";
      }
      container protocol {
        description "Protocol type for controller connection";
        container tcp {
          description "Set protocol type to 'TCP'";
          leaf port {
            type int32 {
              range "1024 .. 65535";
            }
            description "Controller's port number";
          }
        }
        container ssl {
          description "Set protocol type to 'SSL' (default)";
          leaf port {
            type int32 {
              range "1024 .. 65535";
            }
            description "Controller's port number";
          }
        }
      }
      leaf maximum-backoff-duration {
        type uint32 {
          range "1000 .. 4294967295";
        }
        description "Maximum duration to wait between connection attempts";
        units milliseconds;
      }
      leaf inactivity-probe-duration {
        type uint32;
        description "Maximum idle duration before sending inactivity probe";
        units milliseconds;
      }
    }
  }
  grouping juniper-protocols-vni-options {
    list vni {
      description "Per-vni options";
      key name;
      leaf name {
        type int32 {
          range "1 .. 16777214";
        }
      }
      container vrf-target {
        description "VRF target community configuration";
        leaf export {
          type string;
          description "Target community to use when marking routes on export";
          status deprecated;
        }
        leaf community {
          type string;
          description "Target community";
        }
      }
    }
  }
  grouping juniper-protocols-vstp {
    choice enable-disable {
      case case_1 {
        leaf disable {
          type empty;
          description "Disable VSTP";
        }
      }
    }
    leaf force-version {
      type enumeration {
        enum stp {
          description "Spanning tree protocol";
        }
      }
      description "Force protocol version";
    }
    leaf bpdu-block-on-edge {
      type empty;
      description "Block BPDU on all interfaces configured as edge (BPDU Protect)";
    }
    leaf vpls-flush-on-topology-change {
      type empty;
      description "Enable VPLS MAC flush on root protected CE interface receving topology change";
    }
    leaf priority-hold-time {
      type uint16 {
        range "1 .. 255";
      }
      description "Hold time before switching to primary priority when core domain becomes up";
      units seconds;
    }
    list system-id {
      description "System ID to IP mapping";
      key name;
      ordered-by user;
      uses system-id-ip-map;
    }
    list interface {
      description "Interface options";
      key name;
      uses stp-interface;
    }
    list vlan {
      description "VLAN spanning tree options";
      key name;
      leaf name {
        type string;
        description "VLAN id or all";
      }
      leaf bridge-priority {
        type string;
        description "Priority of the bridge (in increments of 4k - 0,4k,8k,..60k)";
      }
      leaf backup-bridge-priority {
        type string;
        description "Priority of the bridge (in increments of 4k - 4k,8k,..60k)";
      }
      leaf max-age {
        type uint16 {
          range "6 .. 40";
        }
        description "Maximum age of received protocol bpdu";
        units seconds;
      }
      leaf hello-time {
        type uint16 {
          range "1 .. 10";
        }
        description "Time interval between configuration BPDUs";
        units seconds;
      }
      leaf forward-delay {
        type uint16 {
          range "4 .. 30";
        }
        description "Time spent in listening or learning state";
        units seconds;
      }
      leaf system-identifier {
        type "jt:mac-unicast";
        description "Sytem identifier to represent this node";
      }
      container traceoptions {
        description "Tracing options for debugging protocol operation";
        uses stp-trace-options;
      }
      list interface {
        description "Interface options";
        key name;
        uses stp-interface;
      }
    }
    container vlan-group {
      description "Spanning tree options for group of VLANs";
      presence "enable vlan-group";
      list group {
        description "Name if VLAN group";
        key name;
        ordered-by user;
        leaf name {
          type string {
            length "1 .. 63";
          }
          description "VLAN group name";
        }
        leaf-list vlan {
          type string;
          description "VLAN ID or VLAN ID range [1..4094]";
          ordered-by user;
        }
        leaf bridge-priority {
          type string;
          description "Priority of the bridge (in increments of 4k - 0,4k,8k,..60k)";
        }
        leaf backup-bridge-priority {
          type string;
          description "Priority of the bridge (in increments of 4k - 4k,8k,..60k)";
        }
        leaf max-age {
          type uint16 {
            range "6 .. 40";
          }
          description "Maximum age of received protocol bpdu";
          units seconds;
        }
        leaf hello-time {
          type uint16 {
            range "1 .. 10";
          }
          description "Time interval between configuration BPDUs";
          units seconds;
        }
        leaf forward-delay {
          type uint16 {
            range "4 .. 30";
          }
          description "Time spent in listening or learning state";
          units seconds;
        }
        leaf system-identifier {
          type "jt:mac-unicast";
          description "Sytem identifier to represent this node";
        }
        container traceoptions {
          description "Tracing options for debugging protocol operation";
          uses stp-trace-options;
        }
        list interface {
          description "Interface options";
          key name;
          uses stp-interface;
        }
      }
    }
  }
  grouping ldp-sync-obj {
    choice enable-disable {
      case case_1 {
        leaf disable {
          type empty;
          description "Disable LDP synchronization";
        }
      }
    }
    leaf hold-time {
      type uint32 {
        range "1 .. 65535";
      }
      description "Time during which maximum metric is advertised";
    }
  }
  grouping ldp_filter_obj {
    description "Filter to apply to tracing";
    leaf match-on {
      type enumeration {
        enum fec {
          description "Filter based on FEC associated to the traced object.";
        }
        enum address {
          description "Filter based on packet source and destination addresses.";
        }
      }
      description "Argument on which to match";
    }
    leaf-list policy {
      type "jt:policy-algebra";
      description "Filter policy";
      ordered-by user;
    }
  }
  grouping lmp_control_channel_type {
    leaf name {
      type "jt:interface-name";
      description "Control channel interface";
    }
    leaf remote-address {
      type "jt:ipaddr";
      description "Control channel remote address";
    }
  }
  grouping lsp-set-match-type {
    leaf lsp-name {
      type string;
      description "LSP name that matches this string";
    }
    leaf lsp-regex {
      type string;
      description "All LSPs that match this regular expression pattern";
    }
    leaf p2mp-name {
      type string;
      description "P2MP names that match this string";
    }
    leaf p2mp-regex {
      type string;
      description "P2MP names that match this regular expression pattern";
    }
    choice router-type {
      case case_1 {
        leaf egress {
          type empty;
          description "All LSPs for which this router is egress";
        }
      }
      case case_2 {
        leaf ingress {
          type empty;
          description "All LSPs for which this router is ingress";
        }
      }
      case case_3 {
        leaf transit {
          type empty;
          description "All LSPs for which this router is transit";
        }
      }
    }
  }
  grouping macro-data-type {
    leaf name {
      type string;
      description "Keyword part of the keyword-value pair";
    }
    leaf value {
      type string;
      description "Value part of the keyword-value pair";
    }
  }
  grouping mrp-trace-options {
    description "Trace options for MMRP Protocol";
    container file {
      description "Trace file options";
      leaf filename {
        type string {
          length "1 .. 1024";
        }
        description "Name of file in which to write trace information";
      }
      leaf replace {
        type empty;
        description "Replace trace file rather than appending to it";
        status deprecated;
      }
      leaf size {
        type string;
        description "Maximum trace file size";
      }
      leaf files {
        type uint32 {
          range "2 .. 1000";
        }
        default "10";
        description "Maximum number of trace files";
      }
      leaf no-stamp {
        type empty;
        description "Do not timestamp trace file";
        status deprecated;
      }
      choice world-readable-choice {
        leaf world-readable {
          type empty;
          description "Allow any user to read the log file";
        }
        leaf no-world-readable {
          type empty;
          description "Don't allow any user to read the log file";
        }
      }
    }
    list flag {
      description "Tracing parameters";
      key name;
      ordered-by user;
      leaf name {
        type enumeration {
          enum events {
            description "Trace events to the protocol state machine";
          }
          enum pdu {
            description "Trace RAPS PDU reception and transmission";
          }
          enum timers {
            description "Trace protocol timers";
          }
          enum state-machine {
            description "Trace information of the state machine";
          }
          enum socket {
            description "Trace soccket activity";
          }
          enum error {
            description "Trace all failure conditions";
          }
          enum all {
            description "Trace all";
          }
        }
      }
      leaf disable {
        type empty;
        description "Disable this trace flag";
      }
    }
  }
  grouping mstp-interface {
    leaf name {
      type string;
    }
    leaf priority {
      type uint16 {
        range "0 .. 255";
      }
      description "Interface priority (in increments of 16 - 0,16,..240)";
    }
    leaf cost {
      type uint32 {
        range "1 .. 200000000";
      }
      description "Cost of the interface";
    }
    leaf mode {
      type enumeration {
        enum point-to-point {
          description "Interface mode is point-to-point";
        }
        enum shared {
          description "Interface mode is shared";
        }
      }
      description "Interface mode (P2P or shared)";
    }
    leaf edge {
      type empty;
      description "Port is an edge port";
    }
    leaf access-trunk {
      type empty;
      description "Send/Receive untagged RSTP BPDUs on this interface";
    }
    container bpdu-timeout-action {
      description "Define action on BPDU expiry (Loop Protect)";
      presence "enable bpdu-timeout-action";
      leaf block {
        type empty;
        description "Block the interface";
      }
      leaf alarm {
        type empty;
        description "Generate an alarm";
      }
    }
    leaf no-root-port {
      type empty;
      description "Do not allow the interface to become root (Root Protect)";
    }
    leaf disable {
      type empty;
      description "Disable Spanning Tree on port";
    }
  }
  grouping pccd-traceoptions-type {
    description "Trace options for PCCD";
    leaf no-remote-trace {
      type empty;
      description "Disable remote tracing";
    }
    container file {
      description "Trace file information";
      leaf filename {
        type string {
          length "1 .. 1024";
        }
        description "Name of file in which to write trace information";
      }
      leaf size {
        type string;
        description "Maximum trace file size";
      }
      leaf files {
        type uint32 {
          range "2 .. 1000";
        }
        default "3";
        description "Maximum number of trace files";
      }
      choice world-readable-choice {
        leaf world-readable {
          type empty;
          description "Allow any user to read the log file";
        }
        leaf no-world-readable {
          type empty;
          description "Don't allow any user to read the log file";
        }
      }
      leaf match {
        type "jt:regular-expression";
        description "Regular expression for lines to be logged";
      }
    }
    list flag {
      description "Area of PCCD to enable debugging output";
      key name;
      ordered-by user;
      leaf name {
        type enumeration {
          enum pccd-main {
            description "Trace main module";
          }
          enum pccd-config {
            description "Trace configuration parsing operations";
          }
          enum pccd-core {
            description "Trace PCCD's core operations";
          }
          enum pccd-ui {
            description "Trace user interface handling";
          }
          enum pccd-rpd {
            description "Trace communication with RPD";
          }
          enum pccd-functions {
            description "Trace function entries/outs";
          }
          enum pccd-nsr {
            description "Trace NSR operations";
          }
          enum all {
            description "Trace all areas of PCCD code";
          }
        }
      }
    }
  }
  grouping peer-group {
    leaf name {
      type "jt:ipv4addr";
      description "IP address for this peer";
    }
    leaf local-ip-addr {
      type "jt:ipv4addr";
      description "Local IP address to use for this peer alone.";
    }
    leaf session-establishment-hold-time {
      type uint32 {
        range "45 .. 600";
      }
      description "Time within which connection must succeed with this peer";
      units seconds;
    }
    leaf-list redundancy-group-id-list {
      type uint32;
      description "List of redundacy groups this peer is part of";
      ordered-by user;
    }
    container backup-liveness-detection {
      description "Backup liveness detection";
      presence "enable backup-liveness-detection";
      leaf backup-peer-ip {
        type "jt:ipv4addr";
        description "Backup livelness detection peer's IP address";
      }
    }
    container liveness-detection {
      description "Bidirectional Forwarding Detection options for the peer";
      presence "enable liveness-detection";
      leaf version {
        type enumeration {
          enum 0 {
            description "BFD version 0 (deprecated)";
          }
          enum 1 {
            description "BFD version 1";
          }
          enum automatic {
            description "Choose BFD version automatically";
          }
        }
        default "automatic";
        description "BFD protocol version number";
      }
      leaf minimum-interval {
        type uint32 {
          range "1 .. 255000";
        }
        description "Minimum transmit and receive interval";
        units milliseconds;
      }
      leaf minimum-transmit-interval {
        type uint32 {
          range "1 .. 255000";
        }
        description "Minimum transmit interval";
        status deprecated;
        units milliseconds;
      }
      leaf minimum-receive-interval {
        type uint32 {
          range "1 .. 255000";
        }
        description "Minimum receive interval";
        units milliseconds;
      }
      leaf multiplier {
        type uint32 {
          range "1 .. 255";
        }
        default "3";
        description "Detection time multiplier";
      }
      leaf inline-disable {
        type empty;
        description "Disable inline mode for this BFD session";
      }
      leaf pdu-size {
        type uint32 {
          range "24 .. 9000";
        }
        default "24";
        description "BFD transport protocol payload size";
      }
      choice adaptation-choice {
        case case_1 {
          leaf no-adaptation {
            type empty;
            description "Disable adaptation";
          }
        }
      }
      container transmit-interval {
        description "Transmit-interval options";
        leaf minimum-interval {
          type uint32 {
            range "1 .. 255000";
          }
          description "Minimum transmit interval";
          units milliseconds;
        }
        leaf threshold {
          type uint32;
          description "High transmit interval triggering a trap";
          units milliseconds;
        }
      }
      container detection-time {
        description "Detection-time options";
        leaf threshold {
          type uint32;
          description "High detection-time triggering a trap";
          units milliseconds;
        }
      }
    }
    leaf authentication-key {
      type string {
        length "1 .. 126";
      }
      description "MD5 authentication key";
    }
  }
  grouping periodic_oam {
    container mpls-tp-mode {
      description "MPLS-TP Mode, Do not use IP addressing for OAM";
      presence "enable mpls-tp-mode";
      container lsping-channel-type {
        description "Supported Control-channel types for MPLS-TP mode....";
        choice action-choice {
          case case_1 {
            leaf ipv4 {
              type empty;
              description "Use channel-type IPv4(0x0021), With IP-UDP encapsulation";
            }
          }
          case case_2 {
            leaf on-demand-cv {
              type empty;
              description "Use channel-type On-Demand-CV(0x0025), Without IP-UDP encapsulation";
            }
          }
        }
      }
    }
    container bfd-port {
      description "Egress knob to select MHOP-BFD port for MPLS BFD";
      leaf-list import {
        type "jt:policy-algebra";
        description "Import policy";
        ordered-by user;
      }
    }
    container bfd-liveness-detection {
      description "Bidirectional Forwarding Detection options";
      leaf version {
        type enumeration {
          enum 0 {
            description "BFD version 0 (deprecated)";
          }
          enum 1 {
            description "BFD version 1";
          }
          enum automatic {
            description "Choose BFD version automatically";
          }
        }
        default "automatic";
        description "BFD protocol version number";
      }
      leaf minimum-interval {
        type uint32 {
          range "1 .. 255000";
        }
        description "Minimum transmit and receive interval";
        units milliseconds;
      }
      leaf minimum-transmit-interval {
        type uint32 {
          range "1 .. 255000";
        }
        description "Minimum transmit interval";
        status deprecated;
        units milliseconds;
      }
      leaf minimum-receive-interval {
        type uint32 {
          range "1 .. 255000";
        }
        description "Minimum receive interval";
        units milliseconds;
      }
      leaf multiplier {
        type uint32 {
          range "1 .. 255";
        }
        default "3";
        description "Detection time multiplier";
      }
      leaf inline-disable {
        type empty;
        description "Disable inline mode for this BFD session";
      }
      leaf pdu-size {
        type uint32 {
          range "24 .. 9000";
        }
        default "24";
        description "BFD transport protocol payload size";
      }
      choice adaptation-choice {
        case case_1 {
          leaf no-adaptation {
            type empty;
            description "Disable adaptation";
          }
        }
      }
      container transmit-interval {
        description "Transmit-interval options";
        leaf minimum-interval {
          type uint32 {
            range "1 .. 255000";
          }
          description "Minimum transmit interval";
          units milliseconds;
        }
        leaf threshold {
          type uint32;
          description "High transmit interval triggering a trap";
          units milliseconds;
        }
      }
      container detection-time {
        description "Detection-time options";
        leaf threshold {
          type uint32;
          description "High detection-time triggering a trap";
          units milliseconds;
        }
      }
      container failure-action {
        description "Action to take when BFD session goes down";
        choice action-choice {
          case case_1 {
            leaf teardown {
              type empty;
              description "Teardown label switched path and resignal";
            }
          }
          case case_2 {
            container make-before-break {
              description "Resignal the label switched path before teardown";
              presence "enable make-before-break";
              leaf teardown-timeout {
                type uint32 {
                  range "0 .. 30";
                }
                description "Time to wait before teardown";
                units seconds;
              }
            }
          }
        }
      }
      leaf no-router-alert-option {
        type empty;
        description "Do not set Router-Alert options in IP header for MPLS-BFD";
      }
      leaf use-ip-ttl-1 {
        type empty;
        description "Set TTL value to 1 in IP header for MPLS-BFD";
      }
    }
    container performance-monitoring {
      description "Performance monitoring options";
      container traceoptions {
        description "Trace options for PM";
        container file {
          description "Trace file options";
          leaf filename {
            type string {
              length "1 .. 1024";
            }
            description "Name of file in which to write trace information";
          }
          leaf replace {
            type empty;
            description "Replace trace file rather than appending to it";
            status deprecated;
          }
          leaf size {
            type string;
            description "Maximum trace file size";
          }
          leaf files {
            type uint32 {
              range "2 .. 1000";
            }
            default "10";
            description "Maximum number of trace files";
          }
          leaf no-stamp {
            type empty;
            description "Do not timestamp trace file";
            status deprecated;
          }
          choice world-readable-choice {
            leaf world-readable {
              type empty;
              description "Allow any user to read the log file";
            }
            leaf no-world-readable {
              type empty;
              description "Don't allow any user to read the log file";
            }
          }
        }
        list flag {
          description "Tracing parameters";
          key name;
          ordered-by user;
          leaf name {
            type enumeration {
              enum init {
                description "Trace init commnad";
              }
              enum error {
                description "Trace error conditions";
              }
              enum event {
                description "Trace state machine events";
              }
              enum general {
                description "Trace general events";
              }
              enum packet {
                description "Trace various packets ";
              }
              enum timer {
                description "Trace timer processing";
              }
              enum all {
                description "Trace everything";
              }
            }
          }
        }
      }
      container querier {
        description "Querier options";
        container loss {
          description "Loss measurement options";
          list traffic-class {
            description "Traffic class specific options";
            key name;
            leaf name {
              type enumeration {
                enum tc-0 {
                  description "Traffic class 0";
                }
                enum tc-1 {
                  description "Traffic class 1";
                }
                enum tc-2 {
                  description "Traffic class 2";
                }
                enum tc-3 {
                  description "Traffic class 3";
                }
                enum tc-4 {
                  description "Traffic class 4";
                }
                enum tc-5 {
                  description "Traffic class 5";
                }
                enum tc-6 {
                  description "Traffic class 6";
                }
                enum tc-7 {
                  description "Traffic class 7";
                }
                enum all {
                  description "All Traffic class";
                }
                enum none {
                  description "No Traffic class";
                }
              }
              description "Traffic class value";
            }
            leaf query-interval {
              type uint32 {
                range "1000 .. 4294967295";
              }
              description "Minimum transmit interval";
              units milliseconds;
            }
            leaf measurement-quantity {
              type enumeration {
                enum bytes {
                  description "Byte loss measurement";
                }
                enum packets {
                  description "Packet loss measurement";
                }
              }
              default "packets";
              description "Loss measurement quantity";
            }
            leaf average-sample-size {
              type uint16 {
                range "1 .. 30";
              }
              description "Number of samples used in average calculation";
            }
            leaf loss-threshold {
              type uint32 {
                range "1 .. 4294967295";
              }
              description "Loss threshold value";
            }
            leaf loss-threshold-window {
              type uint32 {
                range "1 .. 30";
              }
              description "Number of samples for loss threshold calculation";
            }
          }
        }
        container delay {
          description "Delay measurement options";
          list traffic-class {
            description "Traffic class specific options";
            key name;
            leaf name {
              type enumeration {
                enum tc-0 {
                  description "Traffic class 0";
                }
                enum tc-1 {
                  description "Traffic class 1";
                }
                enum tc-2 {
                  description "Traffic class 2";
                }
                enum tc-3 {
                  description "Traffic class 3";
                }
                enum tc-4 {
                  description "Traffic class 4";
                }
                enum tc-5 {
                  description "Traffic class 5";
                }
                enum tc-6 {
                  description "Traffic class 6";
                }
                enum tc-7 {
                  description "Traffic class 7";
                }
                enum all {
                  description "All Traffic classes";
                }
              }
              description "Traffic class value";
            }
            leaf query-interval {
              type uint32 {
                range "1000 .. 4294967295";
              }
              description "Minimum transmit interval";
              units milliseconds;
            }
            leaf padding-size {
              type uint16 {
                range "1 .. 1500";
              }
              description "Size of padding";
            }
            leaf average-sample-size {
              type uint16 {
                range "1 .. 30";
              }
              description "Number of samples used in average calculation";
            }
            leaf twcd-delay-threshold {
              type uint32 {
                range "1 .. 4294967295";
              }
              description "Two way channel delay threshold value";
              units microseconds;
            }
            leaf rtt-delay-threshold {
              type uint32 {
                range "1 .. 4294967295";
              }
              description "Round trip delay threshold value";
              units microseconds;
            }
          }
        }
        container loss-delay {
          description "Combined loss-delay measurement options";
          list traffic-class {
            description "Traffic class specific options";
            key name;
            leaf name {
              type enumeration {
                enum tc-0 {
                  description "Traffic class 0";
                }
                enum tc-1 {
                  description "Traffic class 1";
                }
                enum tc-2 {
                  description "Traffic class 2";
                }
                enum tc-3 {
                  description "Traffic class 3";
                }
                enum tc-4 {
                  description "Traffic class 4";
                }
                enum tc-5 {
                  description "Traffic class 5";
                }
                enum tc-6 {
                  description "Traffic class 6";
                }
                enum tc-7 {
                  description "Traffic class 7";
                }
                enum all {
                  description "All Traffic classes";
                }
                enum none {
                  description "No Traffic class";
                }
              }
              description "Traffic class value";
            }
            leaf query-interval {
              type uint32 {
                range "1000 .. 4294967295";
              }
              description "Minimum transmit interval";
              units milliseconds;
            }
            leaf measurement-quantity {
              type enumeration {
                enum bytes {
                  description "Byte loss measurement";
                }
                enum packets {
                  description "Packet loss measurement";
                }
              }
              default "packets";
              description "Loss measurement quantity";
            }
            leaf padding-size {
              type uint16 {
                range "1 .. 1500";
              }
              description "Size of padding";
            }
            leaf average-sample-size {
              type uint16 {
                range "1 .. 30";
              }
              description "Number of samples used in average calculation";
            }
            leaf loss-threshold {
              type uint32 {
                range "1 .. 4294967295";
              }
              description "Loss threshold value";
            }
            leaf loss-threshold-window {
              type uint32 {
                range "1 .. 30";
              }
              description "Number of samples for loss threshold calculation";
            }
            leaf twcd-delay-threshold {
              type uint32 {
                range "1 .. 4294967295";
              }
              description "Two way channel delay threshold value";
              units microseconds;
            }
            leaf rtt-delay-threshold {
              type uint32 {
                range "1 .. 4294967295";
              }
              description "Round trip delay threshold value";
              units microseconds;
            }
          }
        }
      }
      container responder {
        description "Responder options";
        container loss {
          description "Loss measurement options";
          leaf min-query-interval {
            type uint32 {
              range "1000 .. 4294967295";
            }
            description "Minimum query interval";
            units milliseconds;
          }
        }
        container delay {
          description "Delay measurement options";
          leaf min-query-interval {
            type uint32 {
              range "1000 .. 4294967295";
            }
            description "Minimum query interval";
            units milliseconds;
          }
        }
      }
    }
    leaf lsp-ping-interval {
      type uint16 {
        range "30 .. 3600";
      }
      description "Time interval between LSP ping messages";
      units seconds;
    }
    leaf lsp-ping-multiplier {
      type uint8 {
        range "1 .. 5";
      }
      description "Number of ping reply missed before declaring BFD down";
    }
    container traceoptions {
      description "Trace options for MPLSOAM process";
      leaf no-remote-trace {
        type empty;
        description "Disable remote tracing";
      }
      container file {
        description "Trace file information";
        leaf filename {
          type string {
            length "1 .. 1024";
          }
          description "Name of file in which to write trace information";
        }
        leaf size {
          type string;
          description "Maximum trace file size";
        }
        leaf files {
          type uint32 {
            range "2 .. 1000";
          }
          default "3";
          description "Maximum number of trace files";
        }
        choice world-readable-choice {
          leaf world-readable {
            type empty;
            description "Allow any user to read the log file";
          }
          leaf no-world-readable {
            type empty;
            description "Don't allow any user to read the log file";
          }
        }
        leaf match {
          type "jt:regular-expression";
          description "Regular expression for lines to be logged";
        }
      }
      list flag {
        description "Tracing parameters";
        key name;
        ordered-by user;
        leaf name {
          type enumeration {
            enum configuration {
              description "Trace configuration events";
            }
            enum pipe {
              description "Trace pipe activity";
            }
            enum rpc-packet-details {
              description "Trace RPC packet details";
            }
            enum database {
              description "Trace database activity";
            }
            enum network {
              description "Trace network activity";
            }
            enum traceroute {
              description "Trace traceroute activity";
            }
            enum all {
              description "Trace everything";
            }
          }
        }
      }
    }
  }
  grouping pim_bootstrap_options_type {
    leaf priority {
      type uint32 {
        range "0 .. 255";
      }
      description "Eligibility to be the bootstrap router";
    }
    leaf-list import {
      type "jt:policy-algebra";
      description "Bootstrap import policy";
      ordered-by user;
    }
    leaf-list export {
      type "jt:policy-algebra";
      description "Bootstrap export policy";
      ordered-by user;
    }
  }
  grouping pim_filter_obj {
    description "Filter to apply to tracing";
    leaf match-on {
      type enumeration {
        enum prefix {
          description "Filter based on prefix";
        }
      }
      description "Argument on which to match";
    }
    leaf-list policy {
      type "jt:policy-algebra";
      description "Filter policy";
      ordered-by user;
    }
  }
  grouping pim_rp_group_range_type {
    leaf name {
      type "jt:ipprefix";
    }
    leaf nexthop-hold-time {
      type uint32 {
        range "1 .. 1000";
      }
      description "Nexthop hold time in milliseconds";
      units milliseconds;
    }
  }
  grouping ppp-traceoptions-type {
    description "Trace options for PPP process";
    leaf no-remote-trace {
      type empty;
      description "Disable remote tracing";
    }
    container file {
      description "Trace file information";
      leaf filename {
        type string {
          length "1 .. 1024";
        }
        description "Name of file in which to write trace information";
      }
      leaf size {
        type string;
        description "Maximum trace file size";
      }
      leaf files {
        type uint32 {
          range "2 .. 1000";
        }
        default "3";
        description "Maximum number of trace files";
      }
      choice world-readable-choice {
        leaf world-readable {
          type empty;
          description "Allow any user to read the log file";
        }
        leaf no-world-readable {
          type empty;
          description "Don't allow any user to read the log file";
        }
      }
      leaf match {
        type "jt:regular-expression";
        description "Regular expression for lines to be logged";
      }
    }
    leaf level {
      type enumeration {
        enum error {
          description "Match error conditions";
        }
        enum warning {
          description "Match warning messages";
        }
        enum notice {
          description "Match conditions that should be handled specially";
        }
        enum info {
          description "Match informational messages";
        }
        enum verbose {
          description "Match verbose messages";
        }
        enum all {
          description "Match all levels";
        }
      }
      default "error";
      description "Level of debugging output";
    }
    list flag {
      description "Area of PPP process to enable debugging output";
      key name;
      ordered-by user;
      leaf name {
        type enumeration {
          enum access {
            description "Trace access code";
          }
          enum address-pool {
            description "Trace address pool code";
          }
          enum auth {
            description "Trace authentication code";
          }
          enum chap {
            description "Trace CHAP code";
          }
          enum pap {
            description "Trace PAP code";
          }
          enum config {
            description "Trace configuration code";
          }
          enum ifdb {
            description "Trace interface database code";
          }
          enum lcp {
            description "Trace LCP state machine code";
          }
          enum memory {
            description "Trace memory management code";
          }
          enum message {
            description "Trace message processing code";
          }
          enum mlppp {
            description "Trace MLPPP code";
          }
          enum ncp {
            description "Trace NCP state machine code";
          }
          enum ppp {
            description "Trace PPP protocol processing code";
          }
          enum radius {
            description "Trace RADIUS processing code";
          }
          enum redundancy {
            description "Trace redundancy code";
          }
          enum rtsock {
            description "Trace routing socket code";
          }
          enum session {
            description "Trace session management code";
          }
          enum signal {
            description "Trace signal handling code";
          }
          enum timer {
            description "Trace timer code";
          }
          enum ui {
            description "Trace user interface code";
          }
          enum ci {
            description "Trace ci code";
          }
          enum all {
            description "Trace all areas of code";
          }
        }
      }
    }
  }
  grouping pppoe-traceoptions-type {
    description "Trace options for PPPoE process";
    leaf no-remote-trace {
      type empty;
      description "Disable remote tracing";
    }
    container file {
      description "Trace file information";
      leaf filename {
        type string {
          length "1 .. 1024";
        }
        description "Name of file in which to write trace information";
      }
      leaf size {
        type string;
        description "Maximum trace file size";
      }
      leaf files {
        type uint32 {
          range "2 .. 1000";
        }
        default "3";
        description "Maximum number of trace files";
      }
      choice world-readable-choice {
        leaf world-readable {
          type empty;
          description "Allow any user to read the log file";
        }
        leaf no-world-readable {
          type empty;
          description "Don't allow any user to read the log file";
        }
      }
      leaf match {
        type "jt:regular-expression";
        description "Regular expression for lines to be logged";
      }
    }
    leaf level {
      type enumeration {
        enum error {
          description "Match error conditions";
        }
        enum warning {
          description "Match warning messages";
        }
        enum notice {
          description "Match conditions that should be handled specially";
        }
        enum info {
          description "Match informational messages";
        }
        enum verbose {
          description "Match verbose messages";
        }
        enum all {
          description "Match all levels";
        }
      }
      default "error";
      description "Level of debugging output";
    }
    list flag {
      description "Area of PPPoE process to enable debugging output";
      key name;
      ordered-by user;
      leaf name {
        type enumeration {
          enum config {
            description "Trace configuration code";
          }
          enum events {
            description "Trace event code";
          }
          enum gres {
            description "Trace GRES code";
          }
          enum init {
            description "Trace initialization code";
          }
          enum interface-db {
            description "Trace interface database code";
          }
          enum memory {
            description "Trace memory management code";
          }
          enum protocol {
            description "Trace PPPoE protocol processing code";
          }
          enum rtsock {
            description "Trace routing socket code";
          }
          enum session-db {
            description "Trace Session DB code";
          }
          enum signal {
            description "Trace signal handling code";
          }
          enum state {
            description "Trace state handling code";
          }
          enum stats {
            description "Trace Stats Handling code";
          }
          enum timer {
            description "Trace timer code";
          }
          enum ui {
            description "Trace user interface code";
          }
          enum all {
            description "Trace all areas of code";
          }
        }
      }
    }
    container filter {
      description "Trace filtering";
      presence "enable filter";
      leaf aci {
        type string {
          length "1 .. 64";
        }
        description "Regular expression to match ACI";
      }
      leaf ari {
        type string {
          length "1 .. 64";
        }
        description "Regular expression to match ARI";
      }
      leaf service-name {
        type string {
          length "1 .. 64";
        }
        description "Service name";
      }
      leaf underlying-interface {
        type string;
        description "Underlying interface name";
      }
      container user {
        description "Filter by user name";
        presence "enable user";
        leaf username {
          type string {
            length "1 .. 64";
          }
          description "Name of the user to be filtered";
        }
      }
    }
  }
  grouping r2cp-traceoptions-type {
    description "Trace options for R2CP process";
    leaf no-remote-trace {
      type empty;
      description "Disable remote tracing";
    }
    container file {
      description "Trace file information";
      leaf filename {
        type string {
          length "1 .. 1024";
        }
        description "Name of file in which to write trace information";
      }
      leaf size {
        type string;
        description "Maximum trace file size";
      }
      leaf files {
        type uint32 {
          range "2 .. 1000";
        }
        default "3";
        description "Maximum number of trace files";
      }
      choice world-readable-choice {
        leaf world-readable {
          type empty;
          description "Allow any user to read the log file";
        }
        leaf no-world-readable {
          type empty;
          description "Don't allow any user to read the log file";
        }
      }
      leaf match {
        type "jt:regular-expression";
        description "Regular expression for lines to be logged";
      }
    }
    leaf level {
      type enumeration {
        enum error {
          description "Match error conditions";
        }
        enum warning {
          description "Match warning messages";
        }
        enum notice {
          description "Match conditions that should be handled specially";
        }
        enum info {
          description "Match informational messages";
        }
        enum verbose {
          description "Match verbose messages";
        }
        enum all {
          description "Match all levels";
        }
      }
      default "error";
      description "Level of debugging output";
    }
    list flag {
      description "Area of R2CP process to enable debugging output";
      key name;
      ordered-by user;
      leaf name {
        type enumeration {
          enum configuration {
            description "Trace configuration code";
          }
          enum event {
            description "Trace events";
          }
          enum interface {
            description "Trace interface processing";
          }
          enum node {
            description "Trace node table code";
          }
          enum packet {
            description "Trace packet processing";
          }
          enum rtsock {
            description "Trace routing socket code";
          }
          enum session {
            description "Trace session events";
          }
          enum socket {
            description "Trace socket calls";
          }
          enum timer {
            description "Trace timer code";
          }
          enum virtual-channel {
            description "Trace virtual channel mapping code";
          }
          enum all {
            description "Trace all areas of code";
          }
        }
      }
    }
  }
  grouping rib-inet3 {
    container "inet.3" {
      description "Use inet.3 to exchange labeled unicast routes";
      presence "enable inet.3";
    }
  }
  grouping rib_group_inet_type {
    description "Routing table group";
    leaf ribgroup-name {
      type string;
      description "Name of the routing table group";
    }
  }
  grouping rib_group_type {
    leaf inet-old-style {
      type string;
      description "Name of the IPv4 routing table group";
      status deprecated;
    }
    leaf inet {
      type string;
      description "Name of the IPv4 routing table group";
    }
    leaf inet3 {
      type string;
      description "Name of the IPv4 inet.3 routing table group";
    }
    leaf inet6 {
      type string;
      description "Name of the IPv6 routing table group";
    }
    leaf inet63 {
      type string;
      description "Name of the IPv6 inet6.3 routing table group";
    }
  }
  grouping rip_filter_obj {
    description "Filter to apply to tracing";
    leaf match-on {
      type enumeration {
        enum prefix {
          description "Filter based on prefix";
        }
      }
      description "Argument on which to match";
    }
    leaf-list policy {
      type "jt:policy-algebra";
      description "Filter policy";
      ordered-by user;
    }
  }
  grouping stp-interface {
    leaf name {
      type string;
    }
    leaf priority {
      type uint16 {
        range "0 .. 255";
      }
      description "Interface priority (in increments of 16 - 0,16,..240)";
    }
    leaf cost {
      type uint32 {
        range "1 .. 200000000";
      }
      description "Cost of the interface";
    }
    leaf mode {
      type enumeration {
        enum point-to-point {
          description "Interface mode is point-to-point";
        }
        enum shared {
          description "Interface mode is shared";
        }
      }
      description "Interface mode (P2P or shared)";
    }
    leaf edge {
      type empty;
      description "Port is an edge port";
    }
    leaf access-trunk {
      type empty;
      description "Send/Receive untagged RSTP BPDUs on this interface";
    }
    container bpdu-timeout-action {
      description "Define action on BPDU expiry (Loop Protect)";
      presence "enable bpdu-timeout-action";
      leaf block {
        type empty;
        description "Block the interface";
      }
      leaf alarm {
        type empty;
        description "Generate an alarm";
      }
    }
    leaf no-root-port {
      type empty;
      description "Do not allow the interface to become root (Root Protect)";
    }
    leaf disable {
      type empty;
      description "Disable Spanning Tree on port";
    }
  }
  grouping stp-trace-options {
    description "Trace options for Spanning Tree Protocol";
    container file {
      description "Trace file options";
      leaf filename {
        type string {
          length "1 .. 1024";
        }
        description "Name of file in which to write trace information";
      }
      leaf replace {
        type empty;
        description "Replace trace file rather than appending to it";
        status deprecated;
      }
      leaf size {
        type string;
        description "Maximum trace file size";
      }
      leaf files {
        type uint32 {
          range "2 .. 1000";
        }
        default "10";
        description "Maximum number of trace files";
      }
      leaf no-stamp {
        type empty;
        description "Do not timestamp trace file";
        status deprecated;
      }
      choice world-readable-choice {
        leaf world-readable {
          type empty;
          description "Allow any user to read the log file";
        }
        leaf no-world-readable {
          type empty;
          description "Don't allow any user to read the log file";
        }
      }
    }
    list flag {
      description "Tracing parameters";
      key name;
      ordered-by user;
      leaf name {
        type enumeration {
          enum events {
            description "Trace events to the protocol state machine";
          }
          enum bpdu {
            description "Trace BPDU reception and transmission";
          }
          enum timers {
            description "Trace protocol timers";
          }
          enum port-information-state-machine {
            description "Trace port information state machine";
          }
          enum port-receive-state-machine {
            description "Trace port receive state machine";
          }
          enum port-role-select-state-machine {
            description "Trace port role selection state machine";
          }
          enum port-role-transit-state-machine {
            description "Trace port role transit state machine";
          }
          enum port-state-transit-state-machine {
            description "Trace port state transit state machine";
          }
          enum port-migration-state-machine {
            description "Trace port migration state machine";
          }
          enum port-transmit-state-machine {
            description "Trace port transmit state machine";
          }
          enum topology-change-state-machine {
            description "Trace topology change state machine";
          }
          enum bridge-detection-state-machine {
            description "Trace Bridge detection state machine";
          }
          enum state-machine-variables {
            description "Trace when state machine variables change";
          }
          enum ppmd {
            description "Trace state and events for ppmd process";
          }
          enum all-failures {
            description "Trace all failure conditions";
          }
          enum all {
            description "Trace all";
          }
        }
      }
      leaf disable {
        type empty;
        description "Disable this trace flag";
      }
    }
  }
  grouping subscription-type {
    leaf link-subscription {
      type string;
      default "100";
      description "Link bandwidth percentage for RSVP reservation";
    }
    leaf ct0 {
      type string;
      default "100";
      description "Subscription percentage for traffic class 0";
    }
    leaf ct1 {
      type string;
      default "100";
      description "Subscription percentage for traffic class 1";
    }
    leaf ct2 {
      type string;
      default "100";
      description "Subscription percentage for traffic class 2";
    }
    leaf ct3 {
      type string;
      default "100";
      description "Subscription percentage for traffic class 3";
    }
    list priority {
      description "Subscription percentage for a specific priority";
      key priority-value;
      ordered-by user;
      leaf priority-value {
        type uint32 {
          range "0 .. 7";
        }
        description "Priority for which subscription percent is being configured";
      }
      leaf percent {
        type string;
        description "Subscription percent for the specific priority";
      }
    }
  }
  grouping system-id-ip-map {
    leaf name {
      type "jt:mac-unicast";
    }
    leaf ip-address {
      type "jt:ipv4prefix";
      description "Peer ID (IP Address)";
    }
  }
  grouping te-class-object {
    leaf traffic-class {
      type enumeration {
        enum ct0 {
          description "Traffic class 0";
        }
        enum ct1 {
          description "Traffic class 1";
        }
        enum ct2 {
          description "Traffic class 2";
        }
        enum ct3 {
          description "Traffic class 3";
        }
      }
      description "Traffic class";
    }
    leaf priority {
      type uint32 {
        range "0 .. 7";
      }
      description "Preemption priority for this class";
    }
  }
  grouping timingd-traceoptions {
    description "Trace options for PTP stack and Servo";
    leaf no-remote-trace {
      type empty;
      description "Disable remote tracing";
    }
    container file {
      description "Trace file information";
      leaf filename {
        type string {
          length "1 .. 1024";
        }
        description "Name of file in which to write trace information";
      }
      leaf size {
        type string;
        description "Maximum trace file size";
      }
      leaf files {
        type uint32 {
          range "2 .. 1000";
        }
        default "3";
        description "Maximum number of trace files";
      }
      choice world-readable-choice {
        leaf world-readable {
          type empty;
          description "Allow any user to read the log file";
        }
        leaf no-world-readable {
          type empty;
          description "Don't allow any user to read the log file";
        }
      }
      leaf match {
        type "jt:regular-expression";
        description "Regular expression for lines to be logged";
      }
    }
    leaf level {
      type enumeration {
        enum error {
          description "Match error conditions";
        }
        enum warning {
          description "Match warning messages";
        }
        enum notice {
          description "Match conditions that should be handled specially";
        }
        enum info {
          description "Match informational messages";
        }
        enum verbose {
          description "Match verbose messages";
        }
        enum all {
          description "Match all levels";
        }
      }
      default "error";
      description "Level of debugging output";
    }
    list flag {
      description "Tracing parameters";
      key name;
      ordered-by user;
      leaf name {
        type enumeration {
          enum init {
            description "Trace daemon start-up related events";
          }
          enum routing-socket {
            description "Trace routing-socket events";
          }
          enum ipc {
            description "Trace IPC messages";
          }
          enum configuration {
            description "Trace configuration events";
          }
          enum timer {
            description "Trace Timer events";
          }
          enum event {
            description "Trace generic events";
          }
          enum ptp-bmc {
            description "Trace PTP BMC messages";
          }
          enum ptp-tp {
            description "Trace PTP telecom profile messages";
          }
          enum ptp-sig {
            description "Trace PTP signalling messages";
          }
          enum ptp-mgmt {
            description "Trace PTP management messages";
          }
          enum ptp-servo {
            description "Trace PTP servo messages";
          }
          enum ptp-config {
            description "Trace PTP config messages";
          }
          enum ptp-announce {
            description "Trace PTP announce messages";
          }
          enum ptp-sync {
            description "Trace PTP sync messages";
          }
          enum ptp-delay-req {
            description "Trace PTP delay-req messages";
          }
          enum ptp-delay-resp {
            description "Trace PTP delay-resp messages";
          }
          enum ptp-sig-announce {
            description "Trace PTP sig-announce messages";
          }
          enum ptp-sig-sync {
            description "Trace PTP sig-sync messages";
          }
          enum ptp-sig-delay {
            description "Trace PTP sig-delay messages";
          }
          enum ptp-tie {
            description "Trace PTP TIE messages";
          }
          enum ptp-tc {
            description "Trace PTP TC messages";
          }
          enum ptp-learned-sl {
            description "Trace PTP learned slaves messages";
          }
          enum pkt-io {
            description "Trace PTP packet IO";
          }
          enum all {
            description "Trace everything";
          }
        }
      }
    }
  }
}
