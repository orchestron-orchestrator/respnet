module srl_nokia-network-instance {
  yang-version 1.1;
  namespace "urn:nokia.com:srlinux:net-inst:network-instance";
  prefix srl_nokia-netinst;

  import srl_nokia-common {
    prefix srl_nokia-comm;
  }
  import srl_nokia-icmp {
    prefix srl_nokia-icmp;
  }
  import srl_nokia-interfaces {
    prefix srl_nokia-if;
  }
  import srl_nokia-bridge-table {
    prefix srl_nokia-bridge-table;
  }
  import srl_nokia-bridge-table-mac-learning {
    prefix srl_nokia-bridge-table-mac-learning;
  }
  import srl_nokia-bridge-table-mac-duplication {
    prefix srl_nokia-bridge-table-mac-duplication;
  }
  import srl_nokia-bridge-table-mac-limit {
    prefix srl_nokia-bridge-table-mac-limit;
  }
  import srl_nokia-bridge-table-shg {
    prefix srl_nokia-bridge-table-shg;
  }
  import srl_nokia-connection-point-pseudowires {
    prefix srl_nokia-connection-point-pseudowires;
  }
  import srl_nokia-extensions {
    prefix srl_nokia-ext;
  }
  import srl_nokia-features {
    prefix srl-feat;
  }
  import srl_nokia-routing-policy {
    prefix srl-rpol;
  }

  organization
    "Nokia";
  contact
    "Nokia SR Linux Support
     Web: <http://www.nokia.com>";
  description
    "This yang file gives a description of a network-instance. This may be a Layer 3 forwarding construct such as a virtual routing and forwarding (VRF) instance, or a Layer 2 instance such as a virtual switch instance (VSI). Mixed Layer 2 and Layer 3 instances are also supported.";

  revision 2024-10-31 {
    description
      "SRLinux 24.10.1";
  }
  revision 2024-07-31 {
    description
      "SRLinux 24.7.1";
  }
  revision 2024-03-31 {
    description
      "SRLinux 24.3.1";
  }
  revision 2023-10-31 {
    description
      "SRLinux 23.10.1";
  }
  revision 2023-07-31 {
    description
      "SRLinux 23.7.1";
  }
  revision 2023-03-31 {
    description
      "SRLinux 23.3.1";
  }
  revision 2022-11-30 {
    description
      "SRLinux 22.11.1";
  }
  revision 2022-06-30 {
    description
      "SRLinux 22.6.1";
  }
  revision 2022-03-31 {
    description
      "SRLinux 22.3.1";
  }
  revision 2021-11-30 {
    description
      "SRLinux 21.11.1";
  }
  revision 2021-06-30 {
    description
      "SRLinux 21.6.1";
  }
  revision 2021-03-31 {
    description
      "SRLinux 21.3.1";
  }
  revision 2020-06-30 {
    description
      "SRLinux 20.6.1";
  }
  revision 2019-11-30 {
    description
      "SRLinux 19.11.1";
  }

  typedef network-instance-subintf-name {
    type string {
      length "1..255";
    }
    description
      "User defined name or reference type to a specific subinterface of the form <interface-name>.<subinterface-index>";
  }

  typedef network-instance-vxlan-if-ref {
    type string {
      length "8..17";
      pattern '(vxlan(0|1[0-9][0-9]|2([0-4][0-9]|5[0-5])|[1-9][0-9]|[1-9])\.(0|[1-9](\d){0,8}))';
    }
    description
      "Reference type to a specific vxlan-interface of the form <tunnel-interface-name>.<vxlan-interface-index>";
  }

  identity ni-type {
    description
      "Base type for network instance types.";
  }

  identity host {
    base ni-type;
    if-feature "srl-feat:host-network-instance";
    description
      "A special routing instances that refers to the hosts network instance (i.e. the network namespace of PID 1)";
  }

  identity default {
    base ni-type;
    description
      "A special routing instance which acts as the 'default' routing instance for a network device.";
  }

  identity ip-vrf {
    base ni-type;
    description
      "A private Layer 3 only routing instance.";
  }

  identity mac-vrf {
    if-feature "srl-feat:bridged";
    base ni-type;
    description
      "A private Layer 2 only switching instance.";
  }

  identity vpws {
    if-feature "srl-feat:vpws";
    base ni-type;
    description
      "A private Layer 2 point-to-point instance.";
  }

  grouping network-instance-top {
    description
      "Top-level grouping containing a list of network instances.";
    list network-instance {
      key "name";
      description
        "Network instances configured on the local system";
      leaf name {
        type srl_nokia-comm:restricted-name;
        description
          "A unique name identifying the network instance";
      }
      leaf type {
        type identityref {
          base ni-type;
        }
        default "default";
        description
          "The type of network instance. The value of this leaf
           indicates the type of forwarding entries that should be
           supported by this network instance";
      }
      leaf admin-state {
        type srl_nokia-comm:admin-state;
        default "enable";
        description
          "This leaf contains the configured, desired state of the
           network instance.";
      }
      leaf oper-state {
        config false;
        type srl_nokia-comm:oper-state;
        description
          "This leaf contains the operational state of the network instance.";
      }
      leaf oper-down-reason {
        config false;
        type enumeration {
          enum admin-down;
          enum no-mcid;
        }
        description
          "The reason the network-instance is down";
      }
      leaf oper-mac-vrf-mtu {
        config false;
        type uint16 {
          range "1492..9500";
        }
        units "bytes";
        description
          "Operational l2-mtu of the mac-vrf network-instance. Calculated as the lowest l2-mtu of the bridged subinterfaces associated to the mac-vrf, minus the vlan tags associated
           to that subinterface (lowest mtu subinterface).

           When the mac-vrf has an associated irb subinterface, if the configured irb ip-mtu exceeds the oper-mac-vrf-mtu minus 14 bytes (Ethernet header), then the irb subinterface will remain operationally down.

           The oper-mac-vrf-mtu is only available in mac-vrf network-instances.";
      }
      leaf oper-vpws-mtu {
        if-feature "srl-feat:vpws";
        config false;
        type uint16 {
          range "1492..9500";
        }
        units "bytes";
        description
          "Operational l2-mtu of the vpws network-instance

           Derived from the l2-mtu of the bridged subinterface
           associated to the vpws, minus the vlan tags associated
           to that subinterface.

           The oper-vpws-mtu is only available in vpws network-instances.";
      }
      leaf description {
        type srl_nokia-comm:description;
        description
          "A user-entered description of this network instance.";
      }
      leaf router-id {
        type srl_nokia-comm:dotted-quad;
        must "(../type = 'srl_nokia-netinst:ip-vrf' or ../type = 'srl_nokia-netinst:default')" {
          error-message "Router-id configuration is not possible on network-instance of types other than ip-vrf or default";
        }
        description
          "A identifier for the local network instance - typically
           used within associated routing protocols or signalling
           routing information in another network instance";
      }
      container mpls-forwarding {
        leaf forward-received-packets {
          type boolean;
          must "(../../type = 'srl_nokia-netinst:default')" {
            error-message "MPLS forwarding is not supported in network-instances of types other than default";
          }
          description
            "When set to true, MPLS packets received on any subinterface of the network-instance will be forwarded according to the matching ILM entries.

             When set to false, MPLS packets are discarded if received on any subinterface of the network-instance.

             In the default network-instance the default is 'true'.";
        }
      }
      container ip-forwarding {
        must "(../type = 'srl_nokia-netinst:ip-vrf' or ../type = 'srl_nokia-netinst:default')" {
          error-message "Ip-forwarding configuration is not possible on network-instance of types other than ip-vrf or default";
        }
        presence "Forwarding options";
        description
          "Forwarding options that apply to the entire network instance.";
        leaf receive-ipv4-check {
          type boolean;
          description
            "If set to true then the following check is done on every subinterface of the network-instance: if an IPv4 packet is received on a subinterface and the IPv4 oper-status of this subinterface is down the packet is discarded. If this leaf is set to false then received IPv4 packets are accepted on all subinterfaces of the network-instance that are up, even if they do not have any IPv4 addresses.";
        }
        leaf receive-ipv6-check {
          type boolean;
          description
            "If set to true then the following check is done on every subinterface of the network-instance: if an IPv6 packet is received on a subinterface and the IPv6 oper-status of this subinterface is down the packet is discarded. If this leaf is set to false then received IPv6 packets are accepted on all subinterfaces of the network-instance that are up, even if they do not have any IPv6 addresses.";
        }
        container last-resort-lookup {
          leaf network-instance {
            description
              "A reference to another network-instance in which the system will try to find a matching IP route if this network instance does not have any route to the destination IP";
            type leafref {
              path "/srl_nokia-netinst:network-instance/name";
            }
            must 'not(/network-instance[name=current()]/type = "srl_nokia-netinst:mac-vrf" or /network-instance[name=current()]/type = "srl_nokia-netinst:host")' {
              error-message "Network instance of last-resort must be a default network-instance or an ip-vrf network-instance";
            }
            must 'not(. = ../../../name)' {
              error-message "Network-instance of last-resort must be a different network-instance";
            }
          }
        }
      }
      container ip-load-balancing {
        if-feature "srl-feat:ixr-dnx or srl-feat:trident3 or srl-feat:trident4 or srl-feat:fpcx";
        description
          "Container for IP load-balancing options that are specific to the network-instance";
        list resilient-hash-prefix {
          description
            "List of IPv4 and IPv6 prefixes which should be programmed for resilient ECMP hashing.";
          must "(../../type = 'srl_nokia-netinst:ip-vrf' or ../../type = 'srl_nokia-netinst:default')" {
            error-message "Resilient-hash-prefix configuration is not possible on network-instance of types other than ip-vrf or default";
          }
          key "ip-prefix";
          leaf ip-prefix {
            type srl_nokia-comm:ip-prefix;
            description
              "IPv4 or IPv6 prefix. Active routes in the FIB that exactly match this prefix or that are longer matches of this prefix are provided with resilient-hash programming.";
          }
          leaf hash-buckets-per-path {
            type uint8 {
              range "1..32";
            }
            default "1";
            description
              "The number of times each next-hop is repeated in the fill pattern if there are max-paths ECMP next-hops

               A larger number consumes more resources but provides more granularity when flows need to be moved. There is a platform-specific limit to the product of this hash-buckets-per-path value and the max-paths value.";
          }
          leaf max-paths {
            type uint8 {
              range "1..64";
            }
            default "1";
            description
              "The maximum number of ECMP next-hops per route associated with the resilient-hash prefix

               If a matching route has more than this number of ECMP next-hops only the first N are used, where N is the value of this parameter. There is a platform-specific limit to the product of this max-paths value and the hash-buckets-per-path value.";
          }
        }
      }
      container inter-instance-policies {
        if-feature "srl-feat:route-leaking";
        description
          "Policies for leaking routes between this network instance and other network instances";
        container apply-policy {
          description
            "Container for specifying route leaking import and export policies";
          leaf import-policy {
            description
              "Policy used to specify the routes leaked by other NIs that should be imported into this NI";
            type leafref {
              path "/srl-rpol:routing-policy/srl-rpol:policy/srl-rpol:name";
            }
            must "../../../srl_nokia-netinst:type = 'ip-vrf' or ../../../srl_nokia-netinst:type = 'default'" {
              error-message "Route leaking is only suported in the default and ip-vrf network-instances";
            }
          }
          leaf export-policy {
            description
              "Policy used to specify the routes of this NI that should be made available for leaking to other NIs";
            type leafref {
              path "/srl-rpol:routing-policy/srl-rpol:policy/srl-rpol:name";
            }
            must "../../../srl_nokia-netinst:type = 'ip-vrf' or ../../../srl_nokia-netinst:type = 'default'" {
              error-message "Route leaking is only suported in the default and ip-vrf network-instances";
            }
          }
        }
      }
      grouping interface-bridge-table-top {
        container bridge-table {
          presence "Configure interface bridge-table parameters under a network-instance";
          if-feature "srl-feat:bridged";
          must "../../type = 'srl_nokia-netinst:mac-vrf'" {
            error-message "Bridge-table configuration is only possible on network-instance of type mac-vrf";
          }
          leaf split-horizon-group {
            if-feature "srl-feat:bridged and srl-feat:bt-split-horizon-groups";
            type leafref {
              path "../../../srl_nokia-netinst:bridge-table/srl_nokia-netinst:split-horizon-group/srl_nokia-netinst:name";
            }
            must "not(starts-with(../../name,'irb')) and not(starts-with(../../interface-ref/interface,'irb'))" {
              error-message "split-horizon-group not allowed on IRB interfaces";
            }
          }
          leaf mac-relearn-only {
            config false;
            type boolean;
            default "true";
            description
              "The value of this leaf indicates that the interface will not
               learn any new mac addresses, but will relearn any that are already
               programmed";
          }
          leaf multicast-forwarding {
            config false;
            srl_nokia-ext:show-importance "high";
            type srl_nokia-comm:multicast-type;
            description
              "The type of multicast data forwarded by this subinterface.";
          }
          leaf oper-mac-learning {
            config false;
            type srl_nokia-comm:oper-state;
            description
              "The operational state of mac-learning on this subinterface.";
          }
          leaf oper-mac-learning-disabled-reason {
            config false;
            type enumeration {
              enum admin-disabled;
              enum mac-dup-detected;
            }
            description
              "The reason for the mac-learning being disabled on this interface";
          }
        }
      }

      list interface {
        key "name";
        description
          "List of subinterfaces used by this network-instance";
        must "../type != 'srl_nokia-netinst:host'" {
          error-message "Interfaces cannot be added to a network instance of type host";
        }
        leaf name {
          type srl_nokia-netinst:network-instance-subintf-name;
          description
            "Name of the subinterface bound to this network-instance";
          must "../interface-ref/interface or not(starts-with(.,'lo') and ../../type = 'srl_nokia-netinst:mac-vrf')" {
            error-message "Loopback interfaces cannot be configured on network-instance of type mac-vrf";
          }
          must "../interface-ref/interface or not(starts-with(.,'system') and ../../type != 'srl_nokia-netinst:default')" {
            error-message "System interfaces can only be configured on network-instance of type default";
          }
          must "../interface-ref/interface or /srl_nokia-if:interface[srl_nokia-if:name=substring-before(current(), '.')]/srl_nokia-if:subinterface[srl_nokia-if:index=substring-after(current(), '.')]/srl_nokia-if:type != 'local-mirror-dest'" {
            error-message "subinterface with type local-mirror-dest cannot be configured on network-instance";
          }
          must "../interface-ref/interface or not(starts-with(.,'irb') and ../../bridge-table/proxy-arp)" {
            error-message "IRB interfaces cannot be configured with proxy-arp";
          }
          must "../interface-ref/interface or not(starts-with(.,'irb') and ../../bridge-table/proxy-nd)" {
            error-message "IRB interfaces cannot be configured with proxy-nd";
          }
        }
        container interface-ref {
          if-feature "srl-feat:interface-references";
          description
            "Reference to a subinterface";
          leaf interface {
            type leafref {
              path "/srl_nokia-if:interface/srl_nokia-if:name";
            }
            description
              "Reference to a base interface, for example a port or LAG";
            must '../subinterface >= 0' {
              error-message "subinterface must be configured when interface is set";
            }
            must "not(starts-with(.,'lo') and ../../../type = 'srl_nokia-netinst:mac-vrf')" {
              error-message "Loopback interfaces cannot be configured on network-instance of type mac-vrf";
            }
            must "not(starts-with(.,'system') and ../../../type != 'srl_nokia-netinst:default')" {
              error-message "System interfaces can only be configured on network-instance of type default";
            }
            must "/srl_nokia-if:interface[srl_nokia-if:name=current()]/srl_nokia-if:subinterface[srl_nokia-if:index=current()/../subinterface]/srl_nokia-if:type != 'local-mirror-dest'" {
              error-message "subinterface with type local-mirror-dest cannot be configured on network-instance";
            }
            must "not(starts-with(.,'irb') and ../../../bridge-table/proxy-arp)" {
              error-message "IRB interfaces cannot be configured with proxy-arp";
            }
            must "not(starts-with(.,'irb') and ../../../bridge-table/proxy-nd)" {
              error-message "IRB interfaces cannot be configured with proxy-nd";
            }
          }
          leaf subinterface {
            type leafref {
              path "/srl_nokia-if:interface[srl_nokia-if:name=current()/../interface]/srl_nokia-if:subinterface/srl_nokia-if:index";
            }
            description
              "Reference to a subinterface
               This requires the base interface to be specified using the interface leaf in this container.";
            must '../interface' {
              error-message "interface must be configured when subinterface is set";
            }
          }
        }
        leaf oper-state {
          config false;
          type srl_nokia-comm:oper-state;
          description
            "The operational state of this subinterface.";
        }
        leaf oper-down-reason {
          config false;
          type enumeration {
            enum ip-addr-missing;
            enum ip-addr-overlap;
            enum subif-down;
            enum net-inst-down;
            enum vrf-type-mismatch;
            enum mac-dup-detected;
            enum associated-mac-vrf-down;
            enum mac-vrf-association-missing;
            enum ip-vrf-association-missing;
            enum associated-ip-vrf-down;
            enum evpn-mh-standby;
            enum interface-ref-missing;
          }
          description
            "The reason for the interface being down in the network-instance";
        }
        leaf index {
          config false;
          type uint64;
          default "0";
          description
            "network instance allocated sub interface index";
        }
        uses interface-bridge-table-top;
        leaf connection-point {
          if-feature "srl-feat:connection-point";
          type leafref {
            path "../../srl_nokia-netinst:connection-point/srl_nokia-netinst:name";
          }
          must "not(starts-with(.,'irb'))" {
            error-message "connection-point not allowed on IRB interfaces";
          }
          must "(../../srl_nokia-netinst:type = 'srl_nokia-netinst:vpws')" {
            error-message "Connection-point association to network-instance interfaces is only possible on network-instance of type vpws";
          }
        }
      }
      container system-ipv4-address {
        config false;
        description
          "Container for displaying information about the system IPv4 address of the default network-instance";
        leaf oper-state {
          description
            "The operational state of the system IPv4 address binding";
          type srl_nokia-comm:oper-state;
        }
        leaf oper-down-reason {
          description
            "The reason why the default network instance does not have a system IPv4 address";
          type enumeration {
            enum system-interface-not-bound;
            enum system-interface-has-no-ipv4-address;
          }
        }
      }
      container system-ipv6-address {
        config false;
        description
          "Container for displaying information about the system IPv6 address of the default network-instance";
        leaf oper-state {
          description
            "The operational state of the system IPv6 address binding";
          type srl_nokia-comm:oper-state;
        }
        leaf oper-down-reason {
          description
            "The reason why the default network instance does not have a system IPv6 address";
          type enumeration {
            enum system-interface-not-bound;
            enum system-interface-has-no-ipv6-address;
          }
        }
      }
      list vxlan-interface {
        if-feature "srl-feat:vxlan";
        key "name";
        max-elements 1;
        must '(/srl_nokia-netinst:network-instance[srl_nokia-netinst:name = current()/srl_nokia-netinst:name]/srl_nokia-netinst:type != "srl_nokia-netinst:default")' {
          error-message "The bgp-evpn configuration is not possible on network-instance of type default.";
        }
        description
          "List of vxlan-interfaces used by this network-instance";
        leaf name {
          type srl_nokia-netinst:network-instance-vxlan-if-ref;
          must "(starts-with(.,'vxlan'))" {
            error-message "vxlan-interface name must start with the string vxlan";
          }
          must "../../type != 'srl_nokia-netinst:host'" {
            error-message "vxlan-interface cannot be added to a network instance of type host";
          }
          description
            "Identifier of vxlan-interface used in this network-instance";
        }
        leaf oper-state {
          config false;
          type srl_nokia-comm:oper-state;
          description
            "The operational state of this vxlan-interface.";
        }
        leaf oper-down-reason {
          config false;
          type enumeration {
            enum vxlan-tunnel-down;
            enum net-inst-down;
            enum vxlan-if-default-net-inst-source-address-missing;
            enum vxlan-if-default-net-inst-source-if-down;
            enum vrf-type-mismatch;
            enum no-mcid;
          }
          description
            "The reason for the vxlan-interface being down in the network-instance";
        }
      }
      uses srl_nokia-icmp:icmp-top;
      uses srl_nokia-icmp:icmp6-top;
      container protocols {
        description
          "The routing protocols that are enabled for this
           network-instance.";
        container bgp-evpn {
          if-feature "srl-feat:evpn";
          description
            "Top-level configuration and operational state for BGP Ethernet Virtual Private Networks (EVPN)";
          presence "Configure BGP-EVPN";
          must '(/srl_nokia-netinst:network-instance[srl_nokia-netinst:name = current()/../../srl_nokia-netinst:name]/srl_nokia-netinst:type != "srl_nokia-netinst:default")' {
            error-message "The bgp-evpn configuration is not possible on network-instance of type default.";
          }
        }
        container bgp-ipvpn {
          if-feature "srl-feat:ipvpn";
          description
            "Top-level configuration and operational state for BGP IP Virtual Private Networks (IPVPN)";
          presence "Configure BGP-IPVPN";
          must '(/srl_nokia-netinst:network-instance[srl_nokia-netinst:name = current()/../../srl_nokia-netinst:name]/srl_nokia-netinst:type = "srl_nokia-netinst:ip-vrf")' {
            error-message "The bgp-ipvpn configuration is only possible on network-instance of type ip-vrf";
          }
        }
        container directly-connected {
          if-feature "srl-feat:traffic-engineering-bgpls-directly-connected";
          description
            "Container for handling directly connected routes as a pseudo-protocol";
        }
      }
      container bridge-table {
        presence "Configure bridge-table";
        if-feature "srl-feat:bridged";
        must "../type = 'srl_nokia-netinst:mac-vrf'" {
          error-message "Bridge-table configuration is only possible on network-instance of type mac-vrf";
        }
        uses srl_nokia-bridge-table:bridge-table-top;
        uses srl_nokia-bridge-table-mac-learning:bridge-table-mac-learning-top;
        uses srl_nokia-bridge-table-mac-duplication:bridge-table-mac-duplication-top;
        uses srl_nokia-bridge-table-mac-limit:bridge-table-mac-limit-top;
        uses srl_nokia-bridge-table-shg:bridge-table-split-horizon-groups-top;
      }
      container route-table {
        config false;
      }
      container tunnel-table {
        config false;
      }
      container multicast-forwarding-information-base {
        config false;
      }
      grouping connection-point-oper-state-top {
        leaf oper-state {
          config false;
          type srl_nokia-comm:oper-state;
          description
            "The operational state of this connection-point.";
        }
        leaf oper-down-reason {
          config false;
          type enumeration {
            enum mac-dup-detected;
            enum associations-oper-down;
            enum no-associations;
          }
          description
            "The reason for the connection-point being down in the network-instance";
        }
        leaf index {
          config false;
          type uint64;
          default "0";
          description
            "network instance allocated connection-point index";
        }
      }

      grouping connection-point-bridge-table {
        description
          "Configuration and state for bridge-table";
        container bridge-table {
          presence "Enable Bridge Table configuration and state for connection-points";
          description
            "Enable the Bridge Table on the connection-point and configure associated parameters";
          if-feature "srl-feat:bridged";
          must "../../type = 'srl_nokia-netinst:mac-vrf'" {
            error-message "Bridge-table configuration is only possible on network-instance of type mac-vrf";
          }
          leaf discard-unknown-src-mac {
            type boolean;
            default "false";
            description
              "Discard frames with unknown source mac addresses

               The source mac address of the discarded frame is never learned when this command
               is enabled.";
          }
          leaf split-horizon-group {
            if-feature "srl-feat:bridged and srl-feat:bt-split-horizon-groups";
            type leafref {
              path "../../../srl_nokia-netinst:bridge-table/srl_nokia-netinst:split-horizon-group/srl_nokia-netinst:name";
            }
          }
          container mac-limit {
            description
              "Bridge Table size and thresholds";
            leaf maximum-entries {
              type int32 {
                range "1..8192";
              }
              default "250";
              description
                "Maximum number of mac addresses allowed in the bridge-table";
            }
            leaf warning-threshold-pct {
              type int32 {
                range "6..100";
              }
              default "95";
              description
                "Percentage of the configured max-number-macs over which a warning is triggered

                 The warning message is cleared when the percentage drops below the configured
                 percentage minus 5%";
            }
          }
          container mac-learning {
            leaf admin-state {
              type srl_nokia-comm:admin-state;
              default "enable";
              description
                "Configurable state of the learning procedures for dynamic mac addresses

                 If disabled, the existing macs in the bridge-table will be kept (and refreshed
                 if new frames arrive for them) but no new mac addresses will be learned. Frames
                 with unknown mac addresses are not dropped, unless discard-unknown-src-mac is
                 configured.";
            }
            container aging {
              leaf admin-state {
                type srl_nokia-comm:admin-state;
                default "enable";
                description
                  "Configurable state of the aging for the dynamic mac entries in the bridge table

                   If disabled, dynamically learned mac entries will be programmed in the bridge table
                   until the network instance is disabled.";
              }
            }
          }
          container mac-duplication {
            leaf action {
              type enumeration {
                enum use-net-instance-action {
                  value 0;
                }
                enum stop-learning {
                  value 1;
                }
                enum blackhole {
                  value 2;
                }
                enum oper-down {
                  value 3;
                }
              }
              default "use-net-instance-action";
              description
                "Action to take on all the subinterfaces or pseudowires of the connection-point upon detecting at least one mac addresses as duplicate

                 In particular:
                 - use-net-instance-action: upon detecting a duplicate mac on the subinterface, the action on the connection-point will be
                   inherited from the action configured under network-instance/bridge-table/mac-duplication/action.
                 - oper-down: if configured, upon detecting a duplicate mac on the subinterface, the connection-point objects
                   will be brought oper-down, with oper-down-reason mac-dup-detected. The duplicate macs on the interface will be kept
                   in CPM though, and shown in the duplicate-entries state. In this case, arriving frames on a different subinterface/pw with
                   the duplicate mac as source mac are dropped. Arriving frames on a different subinterface/pw with a destination mac
                   matching the duplicate mac are dropped.
                 - blackhole: upon detecting a duplicate mac on the connection-point, the mac will be blackholed. Any
                   frame received on this or any other subinterface with source mac matching a blackhole mac will be discarded. Any frame
                   received with destination mac matching the blackhole mac will be discarded, although still processed for source mac
                   learning.
                 - stop-learning: upon detecting a duplicate mac on the connection-point, existing macs are kept (and refreshed) but new macs
                   are no longer learned on this subinterface/pw. The duplicate mac will stay learned on the subinterface/pw. Frames arriving to
                   a different subinterface/pw with a source mac matching the duplicate mac will be dropped. Frames arriving to a different
                   subinterface/pw with a destination mac matching the duplicate mac will be forwarded normally.";
            }
          }
        }
      }

      grouping connection-point-top {
        list connection-point {
          max-elements 255;
          if-feature "srl-feat:connection-point";
          must "(../type = 'srl_nokia-netinst:mac-vrf' or ../type = 'srl_nokia-netinst:vpws')" {
            error-message "Connection-point configuration is only possible on network-instance of type mac-vrf or vpws";
          }
          description
            "Connection-point information.";
          key "name";
          leaf name {
            type srl_nokia-comm:name {
              length "1..32";
            }
            description
              "A unique name identifying the connection-point";
          }
          uses connection-point-bridge-table;
          uses connection-point-oper-state-top;
          uses srl_nokia-connection-point-pseudowires:pseudowires-top {
            if-feature "srl-feat:pseudowire";
          }
        }
      }

      uses connection-point-top;
    }
  }

  uses network-instance-top;
}
